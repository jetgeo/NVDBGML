FME workspace Stikkrenner.fmw

Parameters:
- Kommuner = 518,519,520   # komm
- xsd = C:\DATA\Standardisering\NVDB-GML\XSD\NVDBStikkrenneKomplett.xsd   # Application Schema
- schemalocation = http://www.jetlundweb.no/geomatikk/GML/NIFS http://www.jetlundweb.no/geomatikk/GML/NIFS/NVDBStikkrenneKomplett.xsd   # Target xsi:schemaLocation URL
- DestDataset_GML = C:\DATA\Standardisering\NVDB-GML\GML\StikkrennerMGD.gml   # Destination Geography Markup Language (GML) File
- SourceDataset_GDMMAPPERQUADRI = C:\Users\knjetl\NVDB\Prosjekter\StikkrenneMGD_gf.GDD   # Source GDM File
- xfmap_api = $(FME_MF_DIR)API_Mapping.xmp   # xfMap for API-mapping
- xsd_xfmap = $(FME_MF_DIR)NVDB_GML_SchemaMapper.xmp   # XSD xfMap File
- coordsys = EPSG:25833   # Koordinatsystem
- namespace = vegvesen.no.nvdb   # Attribute Value

Readers:
- GDMMAPPERQUADRI_1: GDMMAPPERQUADRI from $(SourceDataset_GDMMAPPERQUADRI)

Writers:
- GML_1: GML to $(DestDataset_GML)

Creator
    NUM = 1
    GEOMTYPE = Geometry Object
    CREATED -> AttributeCreator
AttributeCreator
    ATTR_LIST = _api,https://www.vegvesen.no/nvdb/api/sok?kriterie={lokasjon:{kommune: [$(Kommuner)]},objektTyper:[{id:79,antall:10000}]}
    NUM_SUBSEQUENT_FEATURES = 0
    NUM_PRIOR_FEATURES = 0
    -> NVDBAPI2GML
NVDBAPI2GML
    coordsys = $(coordsys)
    namespace = $(namespace)
    apiString = @Value(_api)
    xsd = $(xsd)
    xsd_xfmap = $(xsd_xfmap)
    xfmap_api = $(xfmap_api)
    -> TestFilter
TestFilter
    DEFAULT_VALUE = egengeometri
    TEST_LIST = BOOL_OP,OR,COMPOSITE_TEST,<Unused>,TEST_CLAUSE,"TEST @Value(egengeometri) != true",veggeometri
    veggeometri -> StikkrenneKulvert (writer GML_1)
    egengeometri -> FeatureMerger [input 1]
FeatureMerger
    SUPPLIERS_FIRST = No
    ATTR_ACCUM_MODE = Merge Supplier
    PROCESS_DUPS = No
    ATTR_CONFLICT_RES = Use Requestor
    JOIN_KEYS = @Value(identifikasjon.Identifikasjon.lokalId) @Value(NVDB_ID) AUTO
    MERGE_TYPE = Attributes Only
    MERGED -> StikkrenneKulvert (writer GML_1)
    NOT_MERGED -> StikkrenneKulvert (writer GML_1)
StikkrenneKulvert (writer GML_1)
    attributes: gml_parent_id xml_buffer, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.synbarhet.codeSpace xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, bruksområde xml_buffer, navn xml_buffer, byggeår xml_int64, produktinformasjon xml_buffer, materialtype xml_buffer, prefabrikkert xml_buffer, retning xml_buffer,
      vinkel xml_buffer, tilknyttetLukkaDren xml_buffer, gjennomløpForElvBekk xml_buffer, typeInnløp xml_buffer, typeUtløp xml_buffer, harInnløpsrist xml_buffer, diameterInnvendig xml_int64, breddeInnvendig xml_int64, høydeInnvendig xml_int64, lengde xml_real64, helningFall xml_real64, tverrsnittsform xml_buffer, overfyllingInnløp xml_real64, overfyllingUtløp xml_real64, tykkelseOverfylling xml_real64, posisjon xml_geometry, senterlinje xml_geometry, fundamentering xml_buffer, varmekabler xml_buffer, antallTininger xml_int64, spesielleProblem xml_buffer, eier xml_buffer, vedlikeholdsansvarlig xml_buffer, område xml_geometry, lineærPosisjon.LineærPosisjonPunkt.lineærreferanseMetode xml_buffer, lineærPosisjon.LineærPosisjonPunkt.felt xml_buffer, lineærPosisjon.LineærPosisjonPunkt.avstandSide xml_real64, lineærPosisjon.LineærPosisjonPunkt.lineærtObjektIdentifikasjon.nilReason xml_buffer, lineærPosisjon.LineærPosisjonPunkt.lineærtObjektIdentifikasjon.gml_remoteSchema xml_buffer, lineærPosisjon.LineærPosisjonPunkt.lineærtObjektIdentifikasjon.xlink_href xml_buffer,
      lineærPosisjon.LineærPosisjonPunkt.lineærtObjektIdentifikasjon.owns xml_boolean, lineærPosisjon.LineærPosisjonPunkt.posisjon xml_real64, assosiertNVDB_Kum{}.nilReason xml_buffer, assosiertNVDB_Kum{}.gml_remoteSchema xml_buffer, assosiertNVDB_Kum{}.xlink_href xml_buffer, assosiertNVDB_Kum{}.owns xml_boolean, assosiertSystemobjekt{}.nilReason xml_buffer, assosiertSystemobjekt{}.gml_remoteSchema xml_buffer, assosiertSystemobjekt{}.xlink_href xml_buffer, assosiertSystemobjekt{}.owns xml_boolean, assosiertTilstandSkadeFUPunkt{}.nilReason xml_buffer, assosiertTilstandSkadeFUPunkt{}.gml_remoteSchema xml_buffer, assosiertTilstandSkadeFUPunkt{}.xlink_href xml_buffer, assosiertTilstandSkadeFUPunkt{}.owns xml_boolean, assosiertTilstandSkadePunkt{}.nilReason xml_buffer, assosiertTilstandSkadePunkt{}.gml_remoteSchema xml_buffer, assosiertTilstandSkadePunkt{}.xlink_href xml_buffer, assosiertTilstandSkadePunkt{}.owns xml_boolean, assosiertNVDB_Kommentar{}.nilReason xml_buffer, assosiertNVDB_Kommentar{}.gml_remoteSchema xml_buffer, assosiertNVDB_Kommentar{}.xlink_href xml_buffer, assosiertNVDB_Kommentar{}.owns xml_boolean, assosiertNVDB_Dokumentasjon{}.nilReason xml_buffer, assosiertNVDB_Dokumentasjon{}.gml_remoteSchema xml_buffer, assosiertNVDB_Dokumentasjon{}.xlink_href xml_buffer, assosiertNVDB_Dokumentasjon{}.owns xml_boolean

Bookmark: Henter kvalitet mm fra QUADRI-base
StikkrenneKulvert_79 (reader GDMMAPPERQUADRI_1)
    attributes: ANTALLTININGER_1942 number(2,0), BRUKSOMRÅDE_6981 number(5,0), BYGGEÅR_4556 number(5,0), DATAFANGSTDATO number(9,0), DIAMETERINNVENDIG_3113 number(5,0), FUNDAMENTERING_6982 number(5,0), GEOMETRITYPE number(2,0), HARINNLØPSRIST_1923 number(5,0), HOB number(8,3), HREF char(4), KVALITET.H-MÅLEMETODE number(3,0), KVALITET.H-NØYAKTIGHET number(4,0), KVALITET.MÅLEMETODE number(3,0), KVALITET.NØYAKTIGHET number(4,0), KVALITET.SYNBARHET number(2,0), LENGDE number(6,3), LENGDE_1323 number(6,3), LTEMA{}.LTEMA number(3,0), MATERIALTYPE_6983 number(5,0), NVDB_ID number(10,0), OBJTYPE char(21), OPPDATERINGSDATO number(13,0), PREFABRIKKERT_6985 number(5,0), PTEMA{}.PTEMA number(3,0), SIDEPOSISJON char(2), TILKNYTTETLUKKADREN_1941 number(5,0), TVERRSNITTSFORM_6984 number(5,0), TYPEINNLØP_1939 number(5,0), TYPEUTLØP_1940 number(5,0), VARMEKABLER_1832 number(5,0),
      VLENKE.VFRADATO number(9,0), VLENKE.VKJORFLT number(3,0), VLENKE.VNR.VEGNUMMER number(4,0), VLENKE.VNR.VEGSTATUS char(2), VLENKE.VNR.VEGTYPE char(2), VLENKE.VPA.HOVEDPARSELL number(4,0), VLENKE.VPA.METER-FRA number(6,0), VLENKE.VPA.METER-TIL number(6,0), X number(11,3), Y number(10,3)
    -> AttributeKeeper
AttributeKeeper
    KEEP_ATTRS = DATAFANGSTDATO,HREF,KVALITET.H-MÅLEMETODE,KVALITET.H-NØYAKTIGHET,KVALITET.MÅLEMETODE,KVALITET.NØYAKTIGHET,KVALITET.SYNBARHET,NVDB_ID,OBJTYPE,OPPDATERINGSDATO
    -> AttributeRenamer_2
Note: Kvalitet, datoer mm fra geometrien
AttributeRenamer_2
    ATTR_LIST = KVALITET.H-MÅLEMETODE,kvalitet.Posisjonskvalitet.målemetodeHøyde,_FME_NO_OP_,KVALITET.H-NØYAKTIGHET,kvalitet.Posisjonskvalitet.nøyaktighetHøyde,_FME_NO_OP_,KVALITET.MÅLEMETODE,kvalitet.Posisjonskvalitet.målemetode,_FME_NO_OP_,KVALITET.NØYAKTIGHET,kvalitet.Posisjonskvalitet.nøyaktighet,_FME_NO_OP_,KVALITET.SYNBARHET,kvalitet.Posisjonskvalitet.synbarhet,_FME_NO_OP_,HREF,høydereferanse,_FME_NO_OP_,DATAFANGSTDATO,datafangstdato,_FME_NO_OP_,OPPDATERINGSDATO,oppdateringsdato,_FME_NO_OP_
    -> DateFormatter
DateFormatter
    DATE_ATTR = datafangstdato
    INVALID_DATE_VALUE = _FME_NO_OP_
    SRCFMT = %Y%m%d
    FMT = %Y"-"%m"-"%d
    -> DateFormatter_2
DateFormatter_2
    DATE_ATTR = oppdateringsdato
    INVALID_DATE_VALUE = _FME_NO_OP_
    SRCFMT = %Y%m%d%H%M
    FMT = %Y"-"%m"-"%d
    -> FeatureMerger [input 2]

FME custom transformer NVDBAPI2GML

Parameters:
- xsd = C:\DATA\Standardisering\NVDB-GML\XSD\NVDBStikkrenneKomplett.xsd   # Application Schema
- apiString = @Value(_api)   # Tekst med kall til API
- xfmap_api = $(FME_MF_DIR)API_Mapping.xmp   # xfMap for API-mapping
- xsd_xfmap = $(FME_MF_DIR)NVDB_GML_SchemaMapper.xmp   # XSD xfMap File
- namespace = vegvesen.no.nvdb   # Attribute Value
- coordsys = EPSG:25833   # Koordinatsystem

Input (input)
    -> HTTPFetcher_2
Note: Henter objekter fra NVDB-API
HTTPFetcher_2
    USE_COOKIES = No
    PROXY_AUTH_METHOD = Basic
    REQUEST_HEADER:
      GET /vegobjekter HTTP/1.1
      Accept: application/vnd.vegvesen.nvdb-v1+xml
    TARGET_URL = @Value(_api)
    SAVE_FILE = No
    RESPONSE_HEADER_LIST_ATTR = _headers
    VERIFY_SSL_CERTIFICATES = Yes
    TARGET_ATTR = _url_contents
    AUTH_METHOD = Basic
    ERROR_ATTR = _error
    STATUS_CODE_ATTR = _http_status_code
    FOLLOW_REDIRECTS = Yes
    -> XMLFeatureMapper
Note: Tolker XML
XMLFeatureMapper
    XML_INPUT_TYPE = Attribute with XML document
    FEATURE_TYPE_ATTR = fme_feature_type
    MERGE_ATTRS = Yes
    SINGLE_XFMAP = $(xfmap_api)
    FEATURE_COUNT_PER_XML = _xml_feature_count_
    CONFIGURATION_TYPE = Single xfMap file
    XML_SOURCE_NAME = _xml_source_
    NEW_ATTRIBUTES = egengeometri geometriUtm33
    ATTRIBUTE_XML = _url_contents
    MAPPED -> GeometryReplacer
Note: Tildeler geometri
GeometryReplacer
    KIND_LONG = OGC Well Known Text
    SOURCE = @Value(geometriUtm33)
    REMOVE_ATTRIBUTE = Yes
    -> CoordinateSystemSetter
CoordinateSystemSetter
    COORDSYS = $(coordsys)
    -> SchemaMapper
Note: Mapper egenskapsnavn til GML, vha applikasjonsskjemaet
SchemaMapper
    IDXDESTCOL = ""
    ROW_ID_ATTR = _schemamapper_row_ids
    XML_CLIP_TO_ENVELOPE = NO
    IDXSOURCEATTR = fme_feature_type
    FORMAT = XML
    XML_USE_HTTP_AUTH = NO
    IDXSOURCECOL = ""
    MAP_ATTRS = NVDB_ID name """"""
    XML_FILE_TYPE = xfMap
    XML_XFMAP = $(xsd_xfmap)
    XML_CONTINUE_ON_GEOM_ERROR = yes
    DATASET = $(xsd)
    TABLE = element
    IDXDESTATTR = fme_feature_type
    MAPPED -> NullAttributeMapper
NullAttributeMapper
    ATTRCHOICE = All Attributes
    NULL_TREATMENT = Missing
    SOURCE_ATTR_VAL = Empty Null
    -> AttributeValueMapper_2
AttributeValueMapper_2
    VAL_ATTR = prosesshistorie
    DEFAULT_VALUE = Geometri: Generert fra lineære referanser til vegnett i NVDB
    DIRECTION = Forward (Source To Destination)
    LUT = true,Geometri: Egengeometri fra NVDB
    SRC = egengeometri
    -> GeometryFilter
AttributeExposer
    ATTR_LIST = NVDB_ID
    -> AttributeRenamer_3
Note: ID
AttributeRenamer_3
    ATTR_LIST = NVDB_ID,identifikasjon.Identifikasjon.lokalId,"","",identifikasjon.Identifikasjon.navnerom,$(namespace)
    -> Output (output)
Output (output)

Bookmark: Definerer geometriegenskaper
GeometryFilter
    GEOM_PORT_NAMES = Point Line Area
    BREAK_AGG = No
    POINT -> GeometryPropertySetter
    LINE -> GeometryPropertySetter_2
    AREA -> GeometryPropertySetter_3
GeometryPropertySetter
    GEOM_NAME_FIELD = posisjon
    SETTYPE_PARAM = Geometry Name
    OVERWRITE_CHOICE = Yes
    SET -> AttributeExposer
GeometryPropertySetter_2
    GEOM_NAME_FIELD = senterlinje
    SETTYPE_PARAM = Geometry Name
    OVERWRITE_CHOICE = Yes
    SET -> AttributeExposer
GeometryPropertySetter_3
    GEOM_NAME_FIELD = område
    SETTYPE_PARAM = Geometry Name
    OVERWRITE_CHOICE = Yes
    SET -> AttributeExposer
