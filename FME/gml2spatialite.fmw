FME workspace gml2spatialite.fmw

Parameters:
- SourceDataset_GML = C:\DATA\GitHub\NVDBGML\GML\Test\kommune\403\vegnett\vegnett.gml   # Source Geography Markup Language (GML) File(s)
- DestDataset_SPATIALITE = C:\DATA\GitHub\NVDBGML\GML\Test\kommune\403\vegnett\vegnett.db   # Destination SpatiaLite Database File

Readers:
- GML_1: GML from $(SourceDataset_GML)

Writers:
- SPATIALITE_1: SPATIALITE to $(DestDataset_SPATIALITE)

Vegnode (reader GML_1)
    attributes: identifikasjon.Identifikasjon.lokalId xml_buffer, identifikasjon.Identifikasjon.navnerom xml_buffer, identifikasjon.Identifikasjon.versjonId xml_buffer, oppdateringsdato xml_datetime, gyldigFra xml_datetime, gyldigTil xml_datetime, datafangstdato xml_datetime, førsteDatafangstdato xml_datetime, førsteDigitaliseringsdato xml_datetime, verifiseringsdato xml_datetime, sluttdato xml_datetime, datauttaksdato xml_datetime, endringsflagg.Endringsflagg.typeEndring xml_buffer, endringsflagg.Endringsflagg.tidspunktEndring xml_datetime, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, status xml_buffer, medium xml_buffer, opphav xml_buffer, digitaliseringsmålestokk xml_int64, prosesshistorie{} xml_buffer, kopidata.Kopidata.områdeId xml_int64, kopidata.Kopidata.originalDatavert xml_buffer, kopidata.Kopidata.kopidato xml_datetime,
      informasjon{} xml_buffer, registreringsversjon.Registreringsversjon.produkt xml_buffer, registreringsversjon.Registreringsversjon.versjon xml_buffer, geodataeier xml_buffer, geodataprodusent xml_buffer, kontaktperson xml_buffer, høydeOverBakken xml_real64, høydereferanse xml_buffer, standardLRM xml_buffer, nettverk{}.nilReason xml_buffer, nettverk{}.gml_remoteSchema xml_buffer, nettverk{}.xlink_href xml_buffer, nettverk{}.owns xml_boolean, nettverkskobling{}.nilReason xml_buffer, nettverkskobling{}.gml_remoteSchema xml_buffer, nettverkskobling{}.xlink_href xml_buffer, nettverkskobling{}.owns xml_boolean, sluttnodeFor{}.nilReason xml_buffer, sluttnodeFor{}.gml_remoteSchema xml_buffer, sluttnodeFor{}.xlink_href xml_buffer, sluttnodeFor{}.owns xml_boolean, startnodeFor{}.nilReason xml_buffer, startnodeFor{}.gml_remoteSchema xml_buffer, startnodeFor{}.xlink_href xml_buffer, startnodeFor{}.owns xml_boolean, posisjon xml_geometry
    -> vegnode (writer SPATIALITE_1)
vegnode (writer SPATIALITE_1)
    attributes: gml_parent_id string(255), gml_parent_property string(255), gml_id string(255), identifikasjon_identifikasjon_lokalid string(255), identifikasjon_identifikasjon_navnerom string(255), identifikasjon_identifikasjon_versjonid string(255), oppdateringsdato string(255), gyldigfra string(255), gyldigtil string(255), datafangstdato string(255), førstedatafangstdato string(255), førstedigitaliseringsdato string(255), verifiseringsdato string(255), sluttdato string(255), datauttaksdato string(255), endringsflagg_endringsflagg_typeendring string(255), endringsflagg_endringsflagg_tidspunktendring string(255), kvalitet_posisjonskvalitet_målemetode string(255), kvalitet_posisjonskvalitet_målemetode_codespace string(255), kvalitet_posisjonskvalitet_nøyaktighet integer64, kvalitet_posisjonskvalitet_synbarhet string(255), kvalitet_posisjonskvalitet_målemetodehøyde string(255), kvalitet_posisjonskvalitet_målemetodehøyde_codespace string(255), kvalitet_posisjonskvalitet_nøyaktighethøyde integer64, kvalitet_posisjonskvalitet_maksimaltavvik integer64, status string(255), medium string(255), opphav string(255), digitaliseringsmålestokk integer64, prosesshistorie__ string(255),
      kopidata_kopidata_områdeid integer64, kopidata_kopidata_originaldatavert string(255), kopidata_kopidata_kopidato string(255), informasjon__ string(255), registreringsversjon_registreringsversjon_produkt string(255), registreringsversjon_registreringsversjon_versjon string(255), geodataeier string(255), geodataprodusent string(255), kontaktperson string(255), høydeoverbakken real(31,15), høydereferanse string(255), standardlrm string(255), nettverk___nilreason string(255), nettverk___gml_remoteschema string(255), nettverk___xlink_href string(255), nettverk___owns integer, nettverkskobling___nilreason string(255), nettverkskobling___gml_remoteschema string(255), nettverkskobling___xlink_href string(255), nettverkskobling___owns integer, sluttnodefor___nilreason string(255), sluttnodefor___gml_remoteschema string(255), sluttnodefor___xlink_href string(255), sluttnodefor___owns integer, startnodefor___nilreason string(255), startnodefor___gml_remoteschema string(255), startnodefor___xlink_href string(255), startnodefor___owns integer, posisjon string(255)
Veglenkesett (reader GML_1)
    attributes: identifikasjon.Identifikasjon.lokalId xml_buffer, identifikasjon.Identifikasjon.navnerom xml_buffer, identifikasjon.Identifikasjon.versjonId xml_buffer, oppdateringsdato xml_datetime, gyldigFra xml_datetime, gyldigTil xml_datetime, datafangstdato xml_datetime, førsteDatafangstdato xml_datetime, førsteDigitaliseringsdato xml_datetime, verifiseringsdato xml_datetime, sluttdato xml_datetime, datauttaksdato xml_datetime, endringsflagg.Endringsflagg.typeEndring xml_buffer, endringsflagg.Endringsflagg.tidspunktEndring xml_datetime, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, status xml_buffer, medium xml_buffer, opphav xml_buffer, digitaliseringsmålestokk xml_int64, prosesshistorie{} xml_buffer, kopidata.Kopidata.områdeId xml_int64, kopidata.Kopidata.originalDatavert xml_buffer, kopidata.Kopidata.kopidato xml_datetime,
      informasjon{} xml_buffer, registreringsversjon.Registreringsversjon.produkt xml_buffer, registreringsversjon.Registreringsversjon.versjon xml_buffer, geodataeier xml_buffer, geodataprodusent xml_buffer, kontaktperson xml_buffer, høydeOverBakken xml_real64, høydereferanse xml_buffer, standardLRM xml_buffer, nettverk{}.nilReason xml_buffer, nettverk{}.gml_remoteSchema xml_buffer, nettverk{}.xlink_href xml_buffer, nettverk{}.owns xml_boolean, nettverkskobling{}.nilReason xml_buffer, nettverkskobling{}.gml_remoteSchema xml_buffer, nettverkskobling{}.xlink_href xml_buffer, nettverkskobling{}.owns xml_boolean, navn xml_buffer, lenke{}.nilReason xml_buffer, lenke{}.gml_remoteSchema xml_buffer, lenke{}.xlink_href xml_buffer, lenke{}.owns xml_boolean
    -> veglenkesett (writer SPATIALITE_1)
veglenkesett (writer SPATIALITE_1)
    attributes: gml_parent_id string(255), gml_parent_property string(255), gml_id string(255), identifikasjon_identifikasjon_lokalid string(255), identifikasjon_identifikasjon_navnerom string(255), identifikasjon_identifikasjon_versjonid string(255), oppdateringsdato string(255), gyldigfra string(255), gyldigtil string(255), datafangstdato string(255), førstedatafangstdato string(255), førstedigitaliseringsdato string(255), verifiseringsdato string(255), sluttdato string(255), datauttaksdato string(255), endringsflagg_endringsflagg_typeendring string(255), endringsflagg_endringsflagg_tidspunktendring string(255), kvalitet_posisjonskvalitet_målemetode string(255), kvalitet_posisjonskvalitet_målemetode_codespace string(255), kvalitet_posisjonskvalitet_nøyaktighet integer64, kvalitet_posisjonskvalitet_synbarhet string(255), kvalitet_posisjonskvalitet_målemetodehøyde string(255), kvalitet_posisjonskvalitet_målemetodehøyde_codespace string(255), kvalitet_posisjonskvalitet_nøyaktighethøyde integer64, kvalitet_posisjonskvalitet_maksimaltavvik integer64, status string(255), medium string(255), opphav string(255), digitaliseringsmålestokk integer64, prosesshistorie__ string(255),
      kopidata_kopidata_områdeid integer64, kopidata_kopidata_originaldatavert string(255), kopidata_kopidata_kopidato string(255), informasjon__ string(255), registreringsversjon_registreringsversjon_produkt string(255), registreringsversjon_registreringsversjon_versjon string(255), geodataeier string(255), geodataprodusent string(255), kontaktperson string(255), høydeoverbakken real(31,15), høydereferanse string(255), standardlrm string(255), nettverk___nilreason string(255), nettverk___gml_remoteschema string(255), nettverk___xlink_href string(255), nettverk___owns integer, nettverkskobling___nilreason string(255), nettverkskobling___gml_remoteschema string(255), nettverkskobling___xlink_href string(255), nettverkskobling___owns integer, navn string(255), lenke___nilreason string(255), lenke___gml_remoteschema string(255), lenke___xlink_href string(255), lenke___owns integer
Veglenkesekvens (reader GML_1)
    attributes: identifikasjon.Identifikasjon.lokalId xml_buffer, identifikasjon.Identifikasjon.navnerom xml_buffer, identifikasjon.Identifikasjon.versjonId xml_buffer, oppdateringsdato xml_datetime, gyldigFra xml_datetime, gyldigTil xml_datetime, datafangstdato xml_datetime, førsteDatafangstdato xml_datetime, førsteDigitaliseringsdato xml_datetime, verifiseringsdato xml_datetime, sluttdato xml_datetime, datauttaksdato xml_datetime, endringsflagg.Endringsflagg.typeEndring xml_buffer, endringsflagg.Endringsflagg.tidspunktEndring xml_datetime, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, status xml_buffer, medium xml_buffer, opphav xml_buffer, digitaliseringsmålestokk xml_int64, prosesshistorie{} xml_buffer, kopidata.Kopidata.områdeId xml_int64, kopidata.Kopidata.originalDatavert xml_buffer, kopidata.Kopidata.kopidato xml_datetime,
      informasjon{} xml_buffer, registreringsversjon.Registreringsversjon.produkt xml_buffer, registreringsversjon.Registreringsversjon.versjon xml_buffer, geodataeier xml_buffer, geodataprodusent xml_buffer, kontaktperson xml_buffer, høydeOverBakken xml_real64, høydereferanse xml_buffer, standardLRM xml_buffer, nettverk{}.nilReason xml_buffer, nettverk{}.gml_remoteSchema xml_buffer, nettverk{}.xlink_href xml_buffer, nettverk{}.owns xml_boolean, nettverkskobling{}.nilReason xml_buffer, nettverkskobling{}.gml_remoteSchema xml_buffer, nettverkskobling{}.xlink_href xml_buffer, nettverkskobling{}.owns xml_boolean, lenke{}.RettaLenke.retning xml_buffer, lenke{}.RettaLenke.lenke.nilReason xml_buffer, lenke{}.RettaLenke.lenke.gml_remoteSchema xml_buffer, lenke{}.RettaLenke.lenke.xlink_href xml_buffer, lenke{}.RettaLenke.lenke.owns xml_boolean
    -> veglenkesekvens (writer SPATIALITE_1)
veglenkesekvens (writer SPATIALITE_1)
    attributes: gml_parent_id string(255), gml_parent_property string(255), gml_id string(255), identifikasjon_identifikasjon_lokalid string(255), identifikasjon_identifikasjon_navnerom string(255), identifikasjon_identifikasjon_versjonid string(255), oppdateringsdato string(255), gyldigfra string(255), gyldigtil string(255), datafangstdato string(255), førstedatafangstdato string(255), førstedigitaliseringsdato string(255), verifiseringsdato string(255), sluttdato string(255), datauttaksdato string(255), endringsflagg_endringsflagg_typeendring string(255), endringsflagg_endringsflagg_tidspunktendring string(255), kvalitet_posisjonskvalitet_målemetode string(255), kvalitet_posisjonskvalitet_målemetode_codespace string(255), kvalitet_posisjonskvalitet_nøyaktighet integer64, kvalitet_posisjonskvalitet_synbarhet string(255), kvalitet_posisjonskvalitet_målemetodehøyde string(255), kvalitet_posisjonskvalitet_målemetodehøyde_codespace string(255), kvalitet_posisjonskvalitet_nøyaktighethøyde integer64, kvalitet_posisjonskvalitet_maksimaltavvik integer64, status string(255), medium string(255), opphav string(255), digitaliseringsmålestokk integer64, prosesshistorie__ string(255),
      kopidata_kopidata_områdeid integer64, kopidata_kopidata_originaldatavert string(255), kopidata_kopidata_kopidato string(255), informasjon__ string(255), registreringsversjon_registreringsversjon_produkt string(255), registreringsversjon_registreringsversjon_versjon string(255), geodataeier string(255), geodataprodusent string(255), kontaktperson string(255), høydeoverbakken real(31,15), høydereferanse string(255), standardlrm string(255), nettverk___nilreason string(255), nettverk___gml_remoteschema string(255), nettverk___xlink_href string(255), nettverk___owns integer, nettverkskobling___nilreason string(255), nettverkskobling___gml_remoteschema string(255), nettverkskobling___xlink_href string(255), nettverkskobling___owns integer, lenke___rettalenke_retning string(255), lenke___rettalenke_lenke_nilreason string(255), lenke___rettalenke_lenke_gml_remoteschema string(255), lenke___rettalenke_lenke_xlink_href string(255), lenke___rettalenke_lenke_owns integer
Veglenke (reader GML_1)
    attributes: identifikasjon.Identifikasjon.lokalId xml_buffer, identifikasjon.Identifikasjon.navnerom xml_buffer, identifikasjon.Identifikasjon.versjonId xml_buffer, oppdateringsdato xml_datetime, gyldigFra xml_datetime, gyldigTil xml_datetime, datafangstdato xml_datetime, førsteDatafangstdato xml_datetime, førsteDigitaliseringsdato xml_datetime, verifiseringsdato xml_datetime, sluttdato xml_datetime, datauttaksdato xml_datetime, endringsflagg.Endringsflagg.typeEndring xml_buffer, endringsflagg.Endringsflagg.tidspunktEndring xml_datetime, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, status xml_buffer, medium xml_buffer, opphav xml_buffer, digitaliseringsmålestokk xml_int64, prosesshistorie{} xml_buffer, kopidata.Kopidata.områdeId xml_int64, kopidata.Kopidata.originalDatavert xml_buffer, kopidata.Kopidata.kopidato xml_datetime,
      informasjon{} xml_buffer, registreringsversjon.Registreringsversjon.produkt xml_buffer, registreringsversjon.Registreringsversjon.versjon xml_buffer, geodataeier xml_buffer, geodataprodusent xml_buffer, kontaktperson xml_buffer, høydeOverBakken xml_real64, høydereferanse xml_buffer, standardLRM xml_buffer, nettverk{}.nilReason xml_buffer, nettverk{}.gml_remoteSchema xml_buffer, nettverk{}.xlink_href xml_buffer, nettverk{}.owns xml_boolean, nettverkskobling{}.nilReason xml_buffer, nettverkskobling{}.gml_remoteSchema xml_buffer, nettverkskobling{}.xlink_href xml_buffer, nettverkskobling{}.owns xml_boolean, måltLengde xml_real64, startposisjon xml_real64, sluttposisjon xml_real64, sluttnode.nilReason xml_buffer, sluttnode.gml_remoteSchema xml_buffer, sluttnode.xlink_href xml_buffer, sluttnode.owns xml_boolean, startnode.nilReason xml_buffer, startnode.gml_remoteSchema xml_buffer, startnode.xlink_href xml_buffer, startnode.owns xml_boolean, typeVeg xml_buffer, detaljnivå xml_buffer,
      konnekteringslenke xml_boolean, veglenkeadresse.Veglenkeadresse.kommunenummer xml_buffer, veglenkeadresse.Veglenkeadresse.adressekode xml_int64, veglenkeadresse.Veglenkeadresse.adressenavn xml_buffer, veglenkeadresse.Veglenkeadresse.sideveg xml_boolean, vegreferanse.Vegreferanse.fylkesnummer xml_buffer, vegreferanse.Vegreferanse.kommunenummer xml_buffer, vegreferanse.Vegreferanse.vegkategori xml_buffer, vegreferanse.Vegreferanse.hovedparsell xml_int64, vegreferanse.Vegreferanse.veglenkeMeterFra xml_int64, vegreferanse.Vegreferanse.veglenkeMeterTil xml_int64, vegreferanse.Vegreferanse.referanseretning xml_buffer, vegreferanse.Vegreferanse.vegreferanseFraDato xml_date, vegreferanse.Vegreferanse.vegreferanseTilDato xml_date, vegreferanse.Vegreferanse.vegstatus xml_buffer, vegreferanse.Vegreferanse.vegnummer xml_int64, feltoversikt xml_buffer, senterlinje xml_geometry
    -> veglenke (writer SPATIALITE_1)
veglenke (writer SPATIALITE_1)
    attributes: gml_parent_id string(255), gml_parent_property string(255), gml_id string(255), identifikasjon_identifikasjon_lokalid string(255), identifikasjon_identifikasjon_navnerom string(255), identifikasjon_identifikasjon_versjonid string(255), oppdateringsdato string(255), gyldigfra string(255), gyldigtil string(255), datafangstdato string(255), førstedatafangstdato string(255), førstedigitaliseringsdato string(255), verifiseringsdato string(255), sluttdato string(255), datauttaksdato string(255), endringsflagg_endringsflagg_typeendring string(255), endringsflagg_endringsflagg_tidspunktendring string(255), kvalitet_posisjonskvalitet_målemetode string(255), kvalitet_posisjonskvalitet_målemetode_codespace string(255), kvalitet_posisjonskvalitet_nøyaktighet integer64, kvalitet_posisjonskvalitet_synbarhet string(255), kvalitet_posisjonskvalitet_målemetodehøyde string(255), kvalitet_posisjonskvalitet_målemetodehøyde_codespace string(255), kvalitet_posisjonskvalitet_nøyaktighethøyde integer64, kvalitet_posisjonskvalitet_maksimaltavvik integer64, status string(255), medium string(255), opphav string(255), digitaliseringsmålestokk integer64, prosesshistorie__ string(255),
      kopidata_kopidata_områdeid integer64, kopidata_kopidata_originaldatavert string(255), kopidata_kopidata_kopidato string(255), informasjon__ string(255), registreringsversjon_registreringsversjon_produkt string(255), registreringsversjon_registreringsversjon_versjon string(255), geodataeier string(255), geodataprodusent string(255), kontaktperson string(255), høydeoverbakken real(31,15), høydereferanse string(255), standardlrm string(255), nettverk___nilreason string(255), nettverk___gml_remoteschema string(255), nettverk___xlink_href string(255), nettverk___owns integer, nettverkskobling___nilreason string(255), nettverkskobling___gml_remoteschema string(255), nettverkskobling___xlink_href string(255), nettverkskobling___owns integer, måltlengde real(31,15), startposisjon real(31,15), sluttposisjon real(31,15), sluttnode_nilreason string(255), sluttnode_gml_remoteschema string(255), sluttnode_xlink_href string(255), sluttnode_owns integer, startnode_nilreason string(255), startnode_gml_remoteschema string(255), startnode_xlink_href string(255),
      startnode_owns integer, typeveg string(255), detaljnivå string(255), konnekteringslenke integer, veglenkeadresse_veglenkeadresse_kommunenummer string(255), veglenkeadresse_veglenkeadresse_adressekode integer64, veglenkeadresse_veglenkeadresse_adressenavn string(255), veglenkeadresse_veglenkeadresse_sideveg integer, vegreferanse_vegreferanse_fylkesnummer string(255), vegreferanse_vegreferanse_kommunenummer string(255), vegreferanse_vegreferanse_vegkategori string(255), vegreferanse_vegreferanse_hovedparsell integer64, vegreferanse_vegreferanse_veglenkemeterfra integer64, vegreferanse_vegreferanse_veglenkemetertil integer64, vegreferanse_vegreferanse_referanseretning string(255), vegreferanse_vegreferanse_vegreferansefradato string(255), vegreferanse_vegreferanse_vegreferansetildato string(255), vegreferanse_vegreferanse_vegstatus string(255), vegreferanse_vegreferanse_vegnummer integer64, feltoversikt string(255), senterlinje string(255)
Nettverkskobling (reader GML_1)
    attributes: nettverkselement{}.nilReason xml_buffer, nettverkselement{}.gml_remoteSchema xml_buffer, nettverkselement{}.xlink_href xml_buffer, nettverkselement{}.owns xml_boolean
    -> nettverkskobling (writer SPATIALITE_1)
nettverkskobling (writer SPATIALITE_1)
    attributes: gml_parent_id string(255), gml_parent_property string(255), gml_id string(255), nettverkselement___nilreason string(255), nettverkselement___gml_remoteschema string(255), nettverkselement___xlink_href string(255), nettverkselement___owns integer
Nettverk (reader GML_1)
    attributes: nettverksnavn xml_buffer, nettverkselement{}.nilReason xml_buffer, nettverkselement{}.gml_remoteSchema xml_buffer, nettverkselement{}.xlink_href xml_buffer, nettverkselement{}.owns xml_boolean
    -> nettverk (writer SPATIALITE_1)
nettverk (writer SPATIALITE_1)
    attributes: gml_parent_id string(255), gml_parent_property string(255), gml_id string(255), nettverksnavn string(255), nettverkselement___nilreason string(255), nettverkselement___gml_remoteschema string(255), nettverkselement___xlink_href string(255), nettverkselement___owns integer
