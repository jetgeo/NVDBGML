FME workspace NVDBAPI2GML_MappingFiles (backup).fmw

Parameters:
- gmlName = OLFV   # GML file and schema name
- ftID = 10   # NVDB feature type ID
- Kommuner = 403   # komm
- xsdFolder = C:\DATA\Standardisering\NVDBGML\XSD\OLFV   # XSD Main folder
- gmlNamespace = https://raw.githubusercontent.com/jetgeo/NVDBGML/master/XSD/OLFV   # GML Namespace
- gmlFolder = C:\DATA\Standardisering\NVDBGML\GML\403   # Output GML folder
- xfmap_api = $(FME_MF_DIR)API_Mapping.xmp   # xfMap for API-mapping
- coordsys = EPSG:25833   # Koordinatsystem
- namespace = vegvesen.no.nvdb   # Attribute Value
- gmlComplete:   # Python Script
      gmlLC = FME_MacroValues['gmlFolder'] + '\\' + FME_MacroValues['gmlName'] + '.gml'
      #Debug
      #print gmlLC
      return gmlLC
- maxFeatures = 10000   # Maximal number of features

Writers:
- GML_1: GML to $(gmlComplete)

Creator
    GEOMTYPE = Geometry Object
    NUM = 1
    CREATED -> AttributeCreator_3
AttributeCreator_3
    ATTR_LIST = ftID,$(ftID)
    -> AttributeSplitter
AttributeSplitter
    DELIMITER = ,
    TRIM_OPTION = Both
    LIST_NAME = _ftID
    ATTR_NAME = ftID
    DROP_EMPTY_PARTS = No
    -> ListExploder
ListExploder
    INDEX_ATTR = _element_index
    ATTR_ACCUM_MODE = Merge Incoming List
    LIST_ATTR = _ftID{}
    ATTR_CONFLICT_RES = Use Original
    LIST_FOUND -> AttributeCreator
    LIST_FOUND -> AttributeCreator_2
    NOT_FOUND -> AttributeCreator_2
    NOT_FOUND -> AttributeCreator
Note: Kunne hente alle objekttyper fra et gitt applikasjonsskjema? / - Lese alle objekttyper i et applikasjonsskjema, med ID, og sende disse til API
Note: AttributeCreator [AttributeCreator:6] / DISABLED / Number of Prior Features: 0 / Number of Subsequent Features: 0 / _api = https://www.vegvesen.no/nvdb/api/sok?kriterie={objektTyper:[{id:@Value(_ftID),antall:$(maxFeatures)}]} / _gmlFeatureType = $(gmlName) / Version: 6 / Last Parameter Edit: Build 15479
AttributeCreator [off]
    ATTR_LIST = _api,https://www.vegvesen.no/nvdb/api/sok?kriterie={objektTyper:[{id:@Value(_ftID),antall:$(maxFeatures)}]},_gmlFeatureType,$(gmlName)
    NUM_SUBSEQUENT_FEATURES = 0
    NUM_PRIOR_FEATURES = 0
    -> NVDBAPI2GML
Note: AttributeCreator_2 [AttributeCreator:6] / Number of Prior Features: 0 / Number of Subsequent Features: 0 / _api = https://www.vegvesen.no/nvdb/api/sok?kriterie={lokasjon:{kommune: [$(Kommuner)]},objektTyper:[{id:@Value(_ftID),antall:$(maxFeatures)}]} / Version: 6 / Last Parameter Edit: Build 15479
AttributeCreator_2
    ATTR_LIST = _api,https://www.vegvesen.no/nvdb/api/sok?kriterie={lokasjon:{kommune: [$(Kommuner)]},objektTyper:[{id:@Value(_ftID),antall:$(maxFeatures)}]}
    NUM_SUBSEQUENT_FEATURES = 0
    NUM_PRIOR_FEATURES = 0
    -> NVDBAPI2GML
NVDBAPI2GML
    mfLocalPrefix = $(xsdFolder)\$(gmlName)
    mfFT:
      mfLC = FME_MacroValues['mfLocalPrefix']+ '_ftMapping.csv'
      return mfLC
    namespace = $(namespace)
    apiString = @Value(_api)
    mfPT:
      mfLC = FME_MacroValues['mfLocalPrefix']+ '_ptMapping.csv'
      return mfLC
    xfmap_api = $(xfmap_api)
    coordsys = $(coordsys)
    -> Vegobjekttype (writer GML_1)
Vegobjekttype (writer GML_1)
    attributes: _creation_instance xml_char(200), ftID xml_char(200), _ftID xml_char(200), _element_index xml_char(200), _api xml_char(200), _gmlFeatureType xml_char(200), _headers{}.name xml_char(200), _headers{}.value xml_char(200), _error xml_char(200), _http_status_code xml_char(200), _url_contents xml_char(200), egengeometri xml_char(200), vegreferanse{}.vegkategori xml_char(200), vegreferanse{}.vegnummer xml_char(200), vegreferanse{}.vegstatus xml_char(200), vegreferanse{}.hovedParsell xml_char(200), vegreferanse{}.veglenkeMeterFra xml_char(200), vegreferanse{}.veglenkeMeterTil xml_char(200), _xml_feature_count_ xml_char(200), _xml_source_ xml_char(200), _schemamapper_row_ids xml_char(200), identifikasjon.Identifikasjon.lokalId xml_buffer, identifikasjon.Identifikasjon.navnerom xml_buffer, prosesshistorie xml_char(200), lineærPosisjon.LineærPosisjonPunkt.lineærtObjektIdentifikasjon.Identifikasjon.lokalId xml_char(200), lineærPosisjon.LineærPosisjonPunkt.posisjon xml_char(200), lineærPosisjon.LineærPosisjonPunkt.tilPosisjon xml_char(200), lineærPosisjon.LineærPosisjonPunkt.felt xml_char(200), _element_count xml_char(200), lineærPosisjon.LineærPosisjonPunkt.lineærtObjektIdentifikasjon.Identifikasjon.navnerom xml_char(200),
      lineærPosisjon{}.LineærPosisjonStrekning.lineærtObjektIdentifikasjon.Identifikasjon.lokalId xml_char(200), lineærPosisjon{}.LineærPosisjonStrekning.fraPosisjon xml_char(200), lineærPosisjon{}.LineærPosisjonStrekning.tilPosisjon xml_char(200), lineærPosisjon{}.LineærPosisjonStrekning.felt xml_char(200), lineærPosisjon{}.identifikasjon.Identifikasjon.lokalId xml_char(200), lineærPosisjon{}._element_count xml_char(200), lineærPosisjon{}._element_index xml_char(200), lineærPosisjon{}.LineærPosisjonStrekning.lineærtObjektIdentifikasjon.Identifikasjon.navnerom xml_char(200)

FME custom transformer NVDBAPI2GML

Parameters:
- apiString = @Value(_api)   # Tekst med kall til API
- xfmap_api = $(FME_MF_DIR)API_Mapping.xmp   # xfMap for API-mapping
- namespace = vegvesen.no.nvdb   # Attribute Value
- coordsys = EPSG:25833   # Koordinatsystem
- mfLocalPrefix =   # Prefiks for mappingfiler
- mfPT:   # Python Script
      mfLC = FME_MacroValues['mfLocalPrefix']+ '_ptMapping.csv'
      return mfLC
- mfFT:   # Python Script
      mfLC = FME_MacroValues['mfLocalPrefix']+ '_ftMapping.csv'
      return mfLC

Input (input)
    -> HTTPFetcher_2
Note: Henter objekter fra NVDB-API
HTTPFetcher_2
    RESPONSE_HEADER_LIST_ATTR = _headers
    REQUEST_HEADER:
      GET /vegobjekter HTTP/1.1
      Accept: application/vnd.vegvesen.nvdb-v1+xml
    ERROR_ATTR = _error
    STATUS_CODE_ATTR = _http_status_code
    VERIFY_SSL_CERTIFICATES = Yes
    FOLLOW_REDIRECTS = Yes
    AUTH_METHOD = Basic
    TARGET_ATTR = _url_contents
    TARGET_URL = @Value(_api)
    PROXY_AUTH_METHOD = Basic
    SAVE_FILE = No
    USE_COOKIES = No
    -> XMLFeatureMapper
Note: Tolker XML
XMLFeatureMapper
    CONFIGURATION_TYPE = Single xfMap file
    FEATURE_TYPE_ATTR = fme_feature_type
    MERGE_ATTRS = Yes
    ATTRIBUTE_XML = _url_contents
    FEATURE_COUNT_PER_XML = _xml_feature_count_
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt
    XML_INPUT_TYPE = Attribute with XML document
    XML_SOURCE_NAME = _xml_source_
    SINGLE_XFMAP = $(xfmap_api)
    MAPPED -> GeometryReplacer
Note: Tildeler geometri
GeometryReplacer
    KIND_LONG = OGC Well Known Text
    SOURCE = @Value(geometriUtm33)
    REMOVE_ATTRIBUTE = Yes
    -> CoordinateSystemSetter
CoordinateSystemSetter
    COORDSYS = $(coordsys)
    -> SchemaMapper_2
Note: SchemaMapper_2 [SchemaMapper:1] / Table Type: CSV / Source: $(mfPT) / Table: CSV / Version: 1 / Last Parameter Edit: Build 15479
Note: Mapper egenskapsnavn til GML, vha koblingstabell
SchemaMapper_2
    IDXSOURCEATTR = fme_feature_type
    DATASET = $(mfPT)
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__DUPLICATE_DELIMS = no
    CSV__STRIP_QUOTES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SKIP_FOOTER = 0
    CSV__SCHEMA = char,17,,number,3,0,number,6,0,char,22,
    IDXDESTATTR = fme_feature_type
    MATCH_ATTRS = ft_attr ftid
    CSV__IN_SEPARATOR = ;
    CSV__GROUP_BY_DATASET = no
    ROW_ID_ATTR = _schemamapper_row_ids
    CSV__IN_FIELD_NAMES = YES
    TABLE = CSV
    FORMAT = CSV
    MAP_ATTRS = ptid name """"""
    CSV__SKIP_LINES = 1
    IDXSOURCECOL = ""
    CSV_SCAN_MAX_FEATURES = 1000
    CSV__FIELD_NAMES_AFTER_HEADER = no
    CSV__ALLOW_SPACES_IN_COLUMN_NAMES = yes
    IDXDESTCOL = ""
    CSV__SCHEMA_WITH_COL_NAMES = ft_attr,char,17,,ftid,number,3,0,ptid,number,6,0,name,char,22,
    MAPPED -> NullAttributeMapper_3
NullAttributeMapper_3
    ATTRCHOICE = All Attributes
    SOURCE_ATTR_VAL = Empty Null
    NULL_TREATMENT = Missing
    -> SchemaMapper_3
Note: SchemaMapper_3 [SchemaMapper:1] / Table Type: CSV / Source: $(mfFT) / Table: CSV / Version: 1 / Last Parameter Edit: Build 15479
Note: Mapperobjekttypenavn til GML, vha koblingstabell
SchemaMapper_3
    IDXSOURCEATTR = fme_feature_type
    DATASET = $(mfFT)
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__DUPLICATE_DELIMS = no
    CSV__STRIP_QUOTES = yes
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SKIP_FOOTER = 0
    CSV__SCHEMA = number,3,0,char,18,
    IDXDESTATTR = fme_feature_type
    CSV__IN_SEPARATOR = ;
    CSV__GROUP_BY_DATASET = no
    ROW_ID_ATTR = _schemamapper_row_ids
    CSV__IN_FIELD_NAMES = YES
    TABLE = CSV
    FORMAT = CSV
    CSV__SKIP_LINES = 1
    IDXSOURCECOL = ftid
    CSV_SCAN_MAX_FEATURES = 1000
    CSV__FIELD_NAMES_AFTER_HEADER = no
    CSV__ALLOW_SPACES_IN_COLUMN_NAMES = yes
    IDXDESTCOL = name
    CSV__SCHEMA_WITH_COL_NAMES = ftid,number,3,0,name,char,18,
    MAPPED -> AttributeExposer_3
AttributeExposer_3
    ATTR_LIST = NVDB_ID
    -> AttributeRenamer_2
Note: ID
AttributeRenamer_2
    ATTR_LIST = NVDB_ID,identifikasjon.Identifikasjon.lokalId,"","",identifikasjon.Identifikasjon.navnerom,$(namespace)
    -> GeometryFilter
AttributeValueMapper_2
    SRC = egengeometri
    DEFAULT_VALUE = Geometri: Generert fra lineære referanser til vegnett i NVDB
    DIRECTION = Forward (Source To Destination)
    VAL_ATTR = prosesshistorie
    LUT = true,Geometri: Egengeometri fra NVDB
    -> AttributeKeeper
    -> AttributeRemover
AttributeRemover
    LIST_ATTRS = lineærPosisjon{}
    -> FeatureMerger [input 1]
AttributeKeeper
    KEEP_LIST = lineærPosisjon{}.felt lineærPosisjon{}.fraPosisjon lineærPosisjon{}.tilPosisjon lineærPosisjon{}.lineærtObjektIdentifikasjon.Identifikasjon.lokalId
    KEEP_ATTRS = identifikasjon.Identifikasjon.lokalId
    -> ListElementCounter
ListElementCounter
    CNT_ATTR = _element_count
    LIST_NAME = lineærPosisjon{}
    -> TestFilter
TestFilter
    DEFAULT_VALUE = Strekning
    TEST_LIST:
      BOOL_OP,AND,COMPOSITE_TEST,<Unused>,TEST_CLAUSE,"TEST @Value(lineærPosisjon{0}.fraPosisjon) = @Value(lineærPosisjon{0}.tilPosisjon)
      TEST @Value(_element_count) = 1",Punkt
    Punkt -> ListExploder
    Strekning -> ListExploder_2
FeatureMerger
    IGNORE_NULLS = No
    ATTR_CONFLICT_RES = Use Requestor
    JOIN_KEYS = @Value(identifikasjon.Identifikasjon.lokalId) @Value(identifikasjon.Identifikasjon.lokalId) AUTO
    SUPPLIERS_FIRST = No
    MERGE_TYPE = Attributes Only
    PROCESS_DUPS = No
    ATTR_ACCUM_MODE = Merge Supplier
    MERGED -> AttributeCreator_2
    NOT_MERGED -> AttributeCreator_2
AttributeCreator_2
    ATTR_LIST = gml_id,$(namespace).@Value(identifikasjon.Identifikasjon.lokalId)
    -> Output (output)
Output (output)

Bookmark: Definerer geometriegenskaper
GeometryFilter
    GEOM_PORT_NAMES = Point Line Area
    BREAK_AGG = No
    POINT -> GeometryPropertySetter
    AREA -> GeometryPropertySetter_3
    LINE -> LineJoiner
    LINE -> FeatureMerger_2 [input 2]
GeometryPropertySetter
    SETTYPE_PARAM = Geometry Name
    GEOM_NAME_FIELD = posisjon
    OVERWRITE_CHOICE = Yes
    SET -> AttributeValueMapper_2
GeometryPropertySetter_3
    SETTYPE_PARAM = Geometry Name
    GEOM_NAME_FIELD = område
    OVERWRITE_CHOICE = Yes
    SET -> AttributeValueMapper_2
Note: Slår sammen linjesegmenter
LineJoiner
    PRESERVE = no
    TOPOLOGY = End noded
    CONSIDER_NODE_ELEVATION = no
    BREAK = no
    LINES_AS_SEGMENTS = No
    GROUP_BY = identifikasjon.Identifikasjon.lokalId
    GROUP_BREAK = no
    LINE -> FeatureMerger_2 [input 1]
FeatureMerger_2
    IGNORE_NULLS = No
    ATTR_CONFLICT_RES = Use Requestor
    JOIN_KEYS = @Value(identifikasjon.Identifikasjon.lokalId) @Value(identifikasjon.Identifikasjon.lokalId) AUTO
    SUPPLIERS_FIRST = No
    MERGE_TYPE = Attributes Only
    PROCESS_DUPS = No
    ATTR_ACCUM_MODE = Merge Supplier
    MERGED -> GeometryPropertySetter_4
GeometryPropertySetter_4
    SETTYPE_PARAM = Geometry Name
    GEOM_NAME_FIELD = senterlinje
    OVERWRITE_CHOICE = Yes
    SET -> AttributeValueMapper_2

Bookmark: Lager lineærPosisjon (punkt)
ListExploder
    INDEX_ATTR = _element_index
    ATTR_ACCUM_MODE = Prefix Incoming List
    LIST_ATTR = lineærPosisjon{}
    INCOMING_PREFIX = lineærPosisjon.LineærPosisjonPunkt.
    LIST_FOUND -> AttributeRenamer
AttributeRenamer
    ATTR_LIST = lineærPosisjon.LineærPosisjonPunkt.fraPosisjon,lineærPosisjon.LineærPosisjonPunkt.posisjon,,,lineærPosisjon.LineærPosisjonPunkt.lineærtObjektIdentifikasjon.Identifikasjon.navnerom,$(namespace).rl
    -> FeatureMerger [input 2]

Bookmark: Lager lineærPosisjon-liste (strekning)
ListExploder_2
    INDEX_ATTR = _element_index
    ATTR_ACCUM_MODE = Prefix Incoming List
    LIST_ATTR = lineærPosisjon{}
    INCOMING_PREFIX = LineærPosisjonStrekning.
    LIST_FOUND -> AttributeCreator
AttributeCreator
    ATTR_LIST = LineærPosisjonStrekning.lineærtObjektIdentifikasjon.Identifikasjon.navnerom,$(namespace).rl
    -> ListBuilder
ListBuilder
    LIST_NAME = lineærPosisjon
    GRP_BY = identifikasjon.Identifikasjon.lokalId
    -> FeatureMerger [input 2]
