FME workspace NVDBAPI2GML_MappingFiles_Paraply.fmw

Parameters:
- gmlName = Stikkrenne   # GML file and schema name
- Kommuner = 519   # komm
- SourceDataset_CSV = C:\DATA\GitHub\NVDBGML\XSD\NIFS\Stikkrenne_ftMapping.csv   # Source CSV (CommaSeparatedValue) File(s)
- xsdFolder = C:\DATA\GitHub\NVDBGML\XSD\NIFS   # XSD Main folder
- gmlNamespace = https://raw.githubusercontent.com/jetgeo/NVDBGML/master/XSD/NIFS   # GML Namespace
- gmlFolder = C:\DATA\GitHub\NVDBGML\GML\NIFS\0520   # Output GML folder

Readers:
- CSV_1: CSV from $(SourceDataset_CSV)

Creator
    GEOMTYPE = Geometry Object
    NUM = 1
    CREATED -> AttributeCreator_3
AttributeCreator_3
    ATTR_LIST = ftID,470,87,86,461,453,81,860,80,209,92,183,843,83,861,78,88,181,876,85,210,828,77,79,853,852
    -> AttributeSplitter
AttributeSplitter
    DELIMITER = ,
    DROP_EMPTY_PARTS = No
    LIST_NAME = _ftID
    ATTR_NAME = ftID
    TRIM_OPTION = Both
    -> ListExploder
ListExploder
    LIST_ATTR = _ftID{}
    ATTR_ACCUM_MODE = Merge Incoming List
    ATTR_CONFLICT_RES = Use Original
    INDEX_ATTR = _element_index
CSV (reader CSV_1)
    attributes: ftid number(4,0), name char(30)
    -> WorkspaceRunner
WorkspaceRunner
    WORKSPACE_PARAMETERS = gmlName,$(gmlName),ftID,@Value(ftid),Kommuner,$(Kommuner),xsdFolder,$(xsdFolder),gmlNamespace,$(gmlNamespace),gmlFolder,$(gmlFolder)
    WORKSPACE_FILE = $(FME_MF_DIR)NVDBAPI2GML_MappingFiles.fmw
    BLOCKING = Yes
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
