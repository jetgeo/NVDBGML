FME workspace xml2none_test.fmw

Parameters:
- ftID = 87   # NVDB Vegobjekttype-ID
- Kommune = 520   # komm
- gmlNs = https://raw.githubusercontent.com/jetgeo/NVDBGML/master/XSD/Test   # GML Namespace
- gmlFolder = C:\DATA\GitHub\NVDBGML\GML\Test   # GML-utmappe
- SourceDataset_XML = ""C:\DATA\GitHub\NVDBGML\API\79.xml" "C:\DATA\GitHub\NVDBGML\API\86.xml" "C:\DATA\GitHub\NVDBGML\API\87.xml""   # Source XML File(s)
- xsd:   # Python Script
      xsd = FME_MacroValues['gmlNs'] + '/' + FME_MacroValues['ftID'] + '.xsd'
      return xsd
- sl:   # Python Script
      sl = FME_MacroValues['gmlNs'] + ' ' + FME_MacroValues['gmlNs'] + '/' + FME_MacroValues['ftID'] + '.xsd'
      return sl
- namespace = vegvesen.no.nvdb   # Attribute Value

Readers:
- XML_1: XML from $(SourceDataset_XML)

Writers:
- GML_1: GML to $(gmlFolder)

Creator
    NUM = 1
    GEOMTYPE = Geometry Object
    CREATED -> HTTPCaller_2
Note: Gjenstår: / [ ] Oversetting av assosiasjoner som er gjort om til datatyper
vegobjekt (reader XML_1) [off]
    attributes: egenskaper.egenskap{}.datatype xml_decimal(3,0), egenskaper.egenskap{}.datatype_tekst xml_char(26), egenskaper.egenskap{}.enhet.id xml_decimal(3,0), egenskaper.egenskap{}.enhet.kortnavn xml_char(4), egenskaper.egenskap{}.enhet.navn xml_char(8), egenskaper.egenskap{}.enum_id xml_decimal(5,0), egenskaper.egenskap{}.id xml_decimal(5,0), egenskaper.egenskap{}.navn xml_char(16), egenskaper.egenskap{}.verdi xml_char(5), geometri.egengeometri xml_char(6), geometri.srid xml_decimal(6,0), geometri.wkt xml_char(65), href xml_char(60), id xml_decimal(9,0), lokasjon.fylker.fylke xml_decimal(2,0), lokasjon.geometri.srid xml_decimal(6,0), lokasjon.geometri.wkt xml_char(65), lokasjon.kommuner.kommune xml_decimal(4,0), lokasjon.kontraktsområder.kontraktsområde.navn xml_char(34), lokasjon.kontraktsområder.kontraktsområde.nummer xml_decimal(4,0), lokasjon.regioner.region xml_decimal(2,0), lokasjon.stedfestinger.stedfesting.kortform xml_char(27), lokasjon.stedfestinger.stedfesting.posisjon xml_decimal(18,16), lokasjon.stedfestinger.stedfesting.retning xml_char(4), lokasjon.stedfestinger.stedfesting.sideposisjon xml_char(2), lokasjon.stedfestinger.stedfesting.veglenkeid xml_decimal(8,0), lokasjon.vegavdelinger.vegavdeling xml_decimal(2,0), lokasjon.vegreferanser.vegreferanse.fylke xml_decimal(2,0), lokasjon.vegreferanser.vegreferanse.hp xml_decimal(2,0), lokasjon.vegreferanser.vegreferanse.kategori xml_char(2),
      lokasjon.vegreferanser.vegreferanse.kommune xml_decimal(2,0), lokasjon.vegreferanser.vegreferanse.kortform xml_char(22), lokasjon.vegreferanser.vegreferanse.meter xml_decimal(6,0), lokasjon.vegreferanser.vegreferanse.nummer xml_decimal(4,0), lokasjon.vegreferanser.vegreferanse.status xml_char(2), metadata.sist_modifisert xml_char(20), metadata.startdato xml_char(11), metadata.type.id xml_decimal(3,0), metadata.type.navn xml_char(19), metadata.versjon xml_decimal(2,0), relasjoner xml_char(1), segmentering.kommuner.kommune xml_decimal(4,0), vegsegmenter.segment.fylke xml_decimal(2,0), vegsegmenter.segment.geometri.srid xml_decimal(6,0), vegsegmenter.segment.geometri.wkt xml_char(65), vegsegmenter.segment.kommune xml_decimal(4,0), vegsegmenter.segment.region xml_decimal(2,0), vegsegmenter.segment.stedfesting.kortform xml_char(27), vegsegmenter.segment.stedfesting.posisjon xml_decimal(18,16), vegsegmenter.segment.stedfesting.retning xml_char(4), vegsegmenter.segment.stedfesting.sideposisjon xml_char(2), vegsegmenter.segment.stedfesting.veglenkeid xml_decimal(8,0), vegsegmenter.segment.vegavdeling xml_decimal(2,0), vegsegmenter.segment.vegreferanse.fylke xml_decimal(2,0), vegsegmenter.segment.vegreferanse.hp xml_decimal(2,0), vegsegmenter.segment.vegreferanse.kategori xml_char(2), vegsegmenter.segment.vegreferanse.kommune xml_decimal(2,0), vegsegmenter.segment.vegreferanse.kortform xml_char(22), vegsegmenter.segment.vegreferanse.meter xml_decimal(6,0), vegsegmenter.segment.vegreferanse.nummer xml_decimal(4,0),
      vegsegmenter.segment.vegreferanse.status xml_char(2), xml_fragment xml_xml, xml_id xml_char(20), xml_matched_element xml_char(10), xml_parent_child_pos xml_char(1), xml_parent_id xml_char(1)
    -> NVDBTranslator
FeatureMerger_3
    ATTR_ACCUM_MODE = Merge Supplier
    JOIN_KEYS = @Value(identifikasjon.Identifikasjon.lokalId) @Value(identifikasjon.Identifikasjon.lokalId) AUTO
    PROCESS_DUPS = No
    MERGE_TYPE = Attributes Only
    REJECT_NULL_MISSING_KEYS = No
    SUPPLIERS_FIRST = No
    ATTR_CONFLICT_RES = Use Requestor
    IGNORE_NULLS = No
    MERGED -> SchemaMapper
    NOT_MERGED -> SchemaMapper
GeometryPropertySetter_SET: Junction
    -> Vegobjekttype (writer GML_1)
    -> Inspector
Inspector
    TACKATTRS = fme_feature_type
Vegobjekttype (writer GML_1)
    attributes: identifikasjon.Identifikasjon.lokalId xml_buffer, id xml_decimal(9,0), geometri.wkt xml_char(65), xml_fragment xml_xml, xml_id xml_char(20), xml_matched_element xml_char(10), xml_parent_id xml_char(1), xml_parent_child_pos xml_char(1), egenskaper.egenskap{}.datatype xml_decimal(3,0), egenskaper.egenskap{}.datatype_tekst xml_char(26), egenskaper.egenskap{}.enhet.id xml_decimal(3,0), egenskaper.egenskap{}.enhet.kortnavn xml_char(4), egenskaper.egenskap{}.enhet.navn xml_char(8), egenskaper.egenskap{}.enum_id xml_decimal(5,0), egenskaper.egenskap{}.id xml_decimal(5,0), egenskaper.egenskap{}.navn xml_char(16), egenskaper.egenskap{}.verdi xml_char(5), geometri.egengeometri xml_char(6), geometri.srid xml_decimal(6,0), href xml_char(60), lokasjon.fylker.fylke xml_decimal(2,0), lokasjon.geometri.srid xml_decimal(6,0), lokasjon.geometri.wkt xml_char(65), lokasjon.kommuner.kommune xml_decimal(4,0), lokasjon.kontraktsområder.kontraktsområde.navn xml_char(34), lokasjon.kontraktsområder.kontraktsområde.nummer xml_decimal(4,0), lokasjon.regioner.region xml_decimal(2,0), lokasjon.stedfestinger.stedfesting.kortform xml_char(27), lokasjon.stedfestinger.stedfesting.posisjon xml_decimal(18,16), lokasjon.stedfestinger.stedfesting.retning xml_char(4),
      lokasjon.stedfestinger.stedfesting.sideposisjon xml_char(2), lokasjon.stedfestinger.stedfesting.veglenkeid xml_decimal(8,0), lokasjon.vegavdelinger.vegavdeling xml_decimal(2,0), lokasjon.vegreferanser.vegreferanse.fylke xml_decimal(2,0), lokasjon.vegreferanser.vegreferanse.hp xml_decimal(2,0), lokasjon.vegreferanser.vegreferanse.kategori xml_char(2), lokasjon.vegreferanser.vegreferanse.kommune xml_decimal(2,0), lokasjon.vegreferanser.vegreferanse.kortform xml_char(22), lokasjon.vegreferanser.vegreferanse.meter xml_decimal(6,0), lokasjon.vegreferanser.vegreferanse.nummer xml_decimal(4,0), lokasjon.vegreferanser.vegreferanse.status xml_char(2), metadata.sist_modifisert xml_char(20), metadata.startdato xml_char(11), metadata.type.id xml_decimal(3,0), metadata.type.navn xml_char(19), metadata.versjon xml_decimal(2,0), relasjoner xml_char(1), segmentering.kommuner.kommune xml_decimal(4,0), vegsegmenter.segment.fylke xml_decimal(2,0), vegsegmenter.segment.geometri.srid xml_decimal(6,0), vegsegmenter.segment.geometri.wkt xml_char(65), vegsegmenter.segment.kommune xml_decimal(4,0), vegsegmenter.segment.region xml_decimal(2,0), vegsegmenter.segment.stedfesting.kortform xml_char(27), vegsegmenter.segment.stedfesting.posisjon xml_decimal(18,16), vegsegmenter.segment.stedfesting.retning xml_char(4), vegsegmenter.segment.stedfesting.sideposisjon xml_char(2), vegsegmenter.segment.stedfesting.veglenkeid xml_decimal(8,0), vegsegmenter.segment.vegavdeling xml_decimal(2,0), vegsegmenter.segment.vegreferanse.fylke xml_decimal(2,0),
      vegsegmenter.segment.vegreferanse.hp xml_decimal(2,0), vegsegmenter.segment.vegreferanse.kategori xml_char(2), vegsegmenter.segment.vegreferanse.kommune xml_decimal(2,0), vegsegmenter.segment.vegreferanse.kortform xml_char(22), vegsegmenter.segment.vegreferanse.meter xml_decimal(6,0), vegsegmenter.segment.vegreferanse.nummer xml_decimal(4,0), vegsegmenter.segment.vegreferanse.status xml_char(2), identifikasjon.Identifikasjon.versjonId xml_char(200), identifikasjon.Identifikasjon.navnerom xml_buffer, assosiasjoner{}.typeId xml_char(200), assosiasjoner{}.vegobjektId xml_char(200), assosiasjoner{}.relasjonstype xml_char(200), name xml_char(200), _schemamapper_row_ids xml_char(200)

Bookmark: Leser og tolker XML fra NVDB-API
Note: Henter vegobjekter fra NVDB-API
HTTPCaller_2
    ERROR_ATTR = _error
    TARGET_ATTR = _url_contents
    TARGET_ATTR_ENCODING = auto-detect
    CUSTOM_HEADERS = Accept;application/vnd.vegvesen.nvdb-v2+xml
    USE_COOKIES = No
    TARGET_URL = https://www.vegvesen.no/nvdb/api/v2/vegobjekter/$(ftID)?kommune=$(Kommune)&antall=100000&inkluder=alle
    CONNECTION_TIMEOUT_LENGTH = 60
    STATUS_CODE_ATTR = _http_status_code
    RESPONSE_HEADER_LIST_ATTR = _headers
    VERIFY_SSL_CERTIFICATES = Yes
    SAVE_FILE = Attribute
    FOLLOW_REDIRECTS = Yes
    HTTP_METHOD = GET
    TRANSFER_TIMEOUT_LENGTH = 90
    -> XMLFragmenter
Note: Deler opp i en XML pr vegobjekt / (gjør påfølgende prosesser raskere)
XMLFragmenter
    NEW_ATTRIBUTES = id geometri.wkt
    MERGE_ATTRS = No
    XML_SOURCE_TYPE = Attribute with XML document
    FEATURE_TYPES_FORMAT_NAME = XML
    EMBEDDED_EXPRESSIONS = vegobjekt
    ATTRIBUTE_XML = _url_contents
    FLATTEN_OPTIONS = <structure separator="." map-empty-elements="yes" matched-prefix="attributes" matched-attributes="yes" cardinality="+{?}" structure-prefix="" child-position-attribute="" except-expression="" ui-mode="basic" matched-ancestor-attributes=""/>
    FRAGMENTS -> NVDBTranslator
Note: Oversetter fra NVDB-API-XML
NVDBTranslator: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype
    PYTHONSOURCE:
      import fme
      import fmeobjects

      def extractNVDB_XML(feature):

          ns=FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  break
              if e == 'None':
                  #Enumverdi for kodelisteverdier
                  feature.setAttribute(n, v)
              else:
                  feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          feature.setAttribute('egengeometri', v)
          feature.removeAttribute('geometri.egengeometri')
          v=feature.getAttribute('geometri.srid')
          feature.setAttribute('epsg', 'EPSG:'+v)
          if v == 'true':
              feature.setAttribute('prosesshistorie', 'Geometri: Generert fra lineære referanser til vegnett i NVDB')
          else:
              feature.setAttribute('prosesshistorie', 'Geometri: Egengeometri fra NVDB')
          feature.removeAttribute('geometri.srid')
          v=feature.getAttribute('geometri.wkt')
          feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting
                          v = str(feature.getAttribute('lokasjon.stedfestinger.stedfesting.veglenkeid'))
                          feature.setAttribute('lineærPosisjon{%d}.LineærPosisjonStrekning.lineærtObjektIdentifikasjon.Identifikasjon.lokalId' % i, v)

                          v = str(feature.getAttribute('lokasjon.stedfestinger.stedfesting.fra_posisjon'))
                          feature.setAttribute('lineærPosisjon{%d}.LineærPosisjonStrekning.fraPosisjon' % i, v)

                          v = str(feature.getAttribute('lokasjon.stedfestinger.stedfesting.til_posisjon'))
                          feature.setAttribute('lineærPosisjon{%d}.LineærPosisjonStrekning.tilPosisjon' % i, v)

                          v = str(feature.getAttribute('lokasjon.stedfestinger.stedfesting.sideposisjon'))
                          if v != 'None':
                              feature.setAttribute('lineærPosisjon{%d}.LineærPosisjonStrekning.sideposisjon' % i, v)

                          v = str(feature.getAttribute('lokasjon.stedfestinger.stedfesting.retning'))
                          if v != 'None':
                              feature.setAttribute('lineærPosisjon{%d}.LineærPosisjonStrekning.retning' % i, v.lower())
                      else:
                          # Punktstedfesting
                          v = str(feature.getAttribute('lokasjon.stedfestinger.stedfesting.veglenkeid'))
                          feature.setAttribute('lineærPosisjon{%d}.LineærPosisjonPunkt.lineærtObjektIdentifikasjon.Identifikasjon.lokalId' % i, v)

                          v = str(feature.getAttribute('lokasjon.stedfestinger.stedfesting.posisjon'))
                          feature.setAttribute('lineærPosisjon{%d}.LineærPosisjonPunkt.posisjon' % i, v)

                          v = str(feature.getAttribute('lokasjon.stedfestinger.stedfesting.sideposisjon'))
                          if v != 'None':
                              feature.setAttribute('lineærPosisjon{%d}.LineærPosisjonPunkt.sideposisjon' % i, v)

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      #print 'Her'
                      v = str(feature.getAttribute('lokasjon.stedfestinger.stedfesting{%d}.veglenkeid' % i))
                      feature.setAttribute('lineærPosisjon{%d}.LineærPosisjonStrekning.lineærtObjektIdentifikasjon.Identifikasjon.lokalId' % i, v)

                      v = str(feature.getAttribute('lokasjon.stedfestinger.stedfesting{%d}.fra_posisjon' % i))
                      feature.setAttribute('lineærPosisjon{%d}.LineærPosisjonStrekning.fraPosisjon' % i, v)

                      v = str(feature.getAttribute('lokasjon.stedfestinger.stedfesting{%d}.til_posisjon' % i))
                      feature.setAttribute('lineærPosisjon{%d}.LineærPosisjonStrekning.tilPosisjon' % i, v)

                      v = str(feature.getAttribute('lokasjon.stedfestinger.stedfesting{%d}.sideposisjon' % i))
                      if v != 'None':
                          feature.setAttribute('lineærPosisjon{%d}.LineærPosisjonStrekning.sideposisjon' % i, v)

                      v = str(feature.getAttribute('lokasjon.stedfestinger.stedfesting{%d}.retning' % i))
                      if v != 'None':
                          feature.setAttribute('lineærPosisjon{%d}.LineærPosisjonStrekning.retning' % i, v.lower())
                  else:
                      # Punktstedfesting
                      v = str(feature.getAttribute('lokasjon.stedfestinger.stedfesting{%d}.veglenkeid' % i))
                      feature.setAttribute('lineærPosisjon{%d}.LineærPosisjonPunkt.lineærtObjektIdentifikasjon.Identifikasjon.lokalId' % i, v)

                      v = str(feature.getAttribute('lokasjon.stedfestinger.stedfesting{%d}.posisjon' % i))
                      feature.setAttribute('lineærPosisjon{%d}.LineærPosisjonPunkt.posisjon' % i, v)

                      v = str(feature.getAttribute('lokasjon.stedfestinger.stedfesting{%d}.sideposisjon' % i))
                      if v != 'None':
                          feature.setAttribute('lineærPosisjon{%d}.LineærPosisjonPunkt.sideposisjon' % i, v)

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      feature.setAttribute('vegreferanse{%d}.Vegreferanse.vegkategori' % i, v)
                      feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedParsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  feature.setAttribute('vegreferanse{%d}.Vegreferanse.vegkategori' % i, v)
                  feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedParsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}')
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}')
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
    -> ListExploder
Note: Geometri
GeometryReplacer
    OGC_WKT_PRECISION_DISPLAY = 64-bit
    KIND_LONG = OGC Well Known Text
    SOURCE = @Value(geometri)
    REMOVE_ATTRIBUTE = Yes
    -> CoordinateSystemSetter
CoordinateSystemSetter
    COORDSYS = EPSG:25833
    -> FeatureMerger_3 [REQUESTOR]

Bookmark: Lager assosiasjonslister med xlink_href
ListExploder
    INDEX_ATTR = _element_index
    LIST_ATTR = assosiasjoner{}
    ATTR_CONFLICT_RES = Use Incoming List
    ATTR_ACCUM_MODE = Merge Incoming List
    ELEMENTS -> AttributeKeeper_2
AttributeKeeper_2
    KEEP_ATTRS = vegobjektId,typeId,identifikasjon.Identifikasjon.navnerom,identifikasjon.Identifikasjon.lokalId,identifikasjon.Identifikasjon.versjonId
    -> Joiner
Joiner
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SCHEMA_WITH_COL_NAMES = ftid,number,4,0,name,char,23,
    ATTR_CONFLICT_RES = Use Original
    FORMAT = CSV
    CSV__FIELD_NAMES_AFTER_HEADER = no
    CSV__GROUP_BY_DATASET = no
    TABLE = CSV
    CSV_SCAN_MAX_FEATURES = 1000
    CSV__DUPLICATE_DELIMS = no
    JOIN_KEYS = typeId ftid
    CSV__STRIP_QUOTES = yes
    CSV__SCHEMA = number,4,0,char,23,
    ADDED_FIELDS = name
    CSV__IN_FIELD_NAMES = YES
    DATASET = https://raw.githubusercontent.com/jetgeo/NVDBGML/master/XSD/NVDB_V206_ftMapping.csv
    MATCH_MULTIPLE_DISPLAY = Create a feature for each match
    CSV__SKIP_FOOTER = 0
    CSV__ALLOW_SPACES_IN_COLUMN_NAMES = yes
    CSV__IN_SEPARATOR = ;
    CSV__SKIP_LINES = 1
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    ATTR_ACCUM_MODE = Merge Joined
    MATCH_RULE_DISPLAY = Match All (1:M)
    JOINED -> StringConcatenator
StringConcatenator
    VAL_ATTR = xlink_href
    PARM_LINE = @Value(name).gml#$(namespace).@Value(vegobjektId)
    ACTION = Create New Attribute
    -> ListBuilder
ListBuilder
    LIST_NAME = _list
    GRP_BY = name identifikasjon.Identifikasjon.navnerom identifikasjon.Identifikasjon.lokalId identifikasjon.Identifikasjon.versjonId
    -> PythonCaller
PythonCaller
    PYTHONSOURCE:
      import fme
      import fmeobjects

      def processFeature(feature):
          anames= feature.getAllAttributeNames()
          lname = "blank"
          #find name attribute value
          for aname in anames:
              if aname == "name":
                  lname = feature.getAttribute(aname)
          #find list attributes and rename/copy to new name
          if lname != "blank":
              for aname in anames:
                  if aname.startswith("_list{"):
                      newAname=aname.replace("_list{","assosiert"+lname+"{")
                      aval = feature.getAttribute(aname)
                      feature.setAttribute(newAname, aval)
    PYTHONSYMBOL = processFeature
    -> AttributeRemover_2
AttributeRemover_2
    LIST_ATTRS = _list{}
    -> FeatureMerger_3 [SUPPLIER]

Bookmark: Oversetter til GML-verdier og -navn
Note: Oversetter tillatte verdier til GML-verdier
SchemaMapper
    CSV__ALLOW_SPACES_IN_COLUMN_NAMES = yes
    IDXSOURCECOL = ""
    CSV__FIELD_NAMES_AFTER_HEADER = no
    CSV__IN_SEPARATOR = ;
    FORMAT = CSV
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    IDXSOURCEATTR = fme_feature_type
    CSV__GROUP_BY_DATASET = no
    IDXDESTCOL = ""
    MATCH_ATTRS = ptid enid
    CSV__SCHEMA = number,6,0,number,6,0,char,29,,char,34,
    TABLE = CSV
    ROW_ID_ATTR = _schemamapper_row_ids
    CSV__DUPLICATE_DELIMS = no
    DATASET = https://raw.githubusercontent.com/jetgeo/NVDBGML/master/XSD/NVDB_V206_enMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    MAP_ATTRS = enid ptid name
    IDXDESTATTR = fme_feature_type
    CSV__SCHEMA_WITH_COL_NAMES = ptid,number,6,0,enid,number,6,0,name,char,29,,fullname,char,34,
    CSV__IN_FIELD_NAMES = YES
    CSV_SCAN_MAX_FEATURES = 1000
    CSV__SKIP_LINES = 1
    MAPPED -> SchemaMapper_2
    UNMAPPED -> SchemaMapper_2
Note: Oversetter egenskapsnavn til GML-navn
SchemaMapper_2
    CSV__ALLOW_SPACES_IN_COLUMN_NAMES = yes
    IDXSOURCECOL = ""
    CSV__FIELD_NAMES_AFTER_HEADER = no
    CSV__IN_SEPARATOR = ;
    FORMAT = CSV
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXSOURCEATTR = fme_feature_type
    CSV__GROUP_BY_DATASET = no
    IDXDESTCOL = ""
    MATCH_ATTRS = ft_attr ftid
    CSV__SCHEMA = char,17,,number,3,0,number,6,0,char,22,
    TABLE = CSV
    ROW_ID_ATTR = _schemamapper_row_ids
    CSV__DUPLICATE_DELIMS = no
    DATASET = https://raw.githubusercontent.com/jetgeo/NVDBGML/master/XSD/NVDB_V206_ptMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    MAP_ATTRS = ptid name """"""
    IDXDESTATTR = fme_feature_type
    CSV__SCHEMA_WITH_COL_NAMES = ft_attr,char,17,,ftid,number,3,0,ptid,number,6,0,name,char,22,
    CSV__IN_FIELD_NAMES = YES
    CSV_SCAN_MAX_FEATURES = 1000
    CSV__SKIP_LINES = 1
    MAPPED -> NullAttributeMapper_3
    UNMAPPED -> NullAttributeMapper_3
NullAttributeMapper_3
    NULL_TREATMENT = Missing
    ATTRCHOICE = All Attributes
    SOURCE_ATTR_VAL = Empty Null
    -> SchemaMapper_3
Note: Oversetter objekttypenavn til GML-navn
SchemaMapper_3
    CSV__ALLOW_SPACES_IN_COLUMN_NAMES = yes
    IDXSOURCECOL = ftid
    CSV__FIELD_NAMES_AFTER_HEADER = no
    CSV__IN_SEPARATOR = ;
    FORMAT = CSV
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCEATTR = fme_feature_type
    CSV__GROUP_BY_DATASET = no
    IDXDESTCOL = name
    CSV__SCHEMA = number,3,0,char,18,
    TABLE = CSV
    ROW_ID_ATTR = _schemamapper_row_ids
    CSV__DUPLICATE_DELIMS = no
    DATASET = https://raw.githubusercontent.com/jetgeo/NVDBGML/master/XSD/NVDB_V206_ftMapping.csv
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    IDXDESTATTR = fme_feature_type
    CSV__SCHEMA_WITH_COL_NAMES = ftid,number,3,0,name,char,18,
    CSV__IN_FIELD_NAMES = YES
    CSV_SCAN_MAX_FEATURES = 1000
    CSV__SKIP_LINES = 1
    MAPPED -> GeometryFilter
    UNMAPPED -> GeometryFilter

Bookmark: Definerer geometriegenskaper
GeometryFilter
    BREAK_AGG = No
    GEOM_PORT_NAMES = Point Line Area
    POINT -> GeometryPropertySetter
    LINE -> LineJoiner
    LINE -> FeatureMerger_2 [SUPPLIER]
    AREA -> GeometryPropertySetter_3
GeometryPropertySetter
    OVERWRITE_CHOICE = Yes
    GEOM_NAME_FIELD = posisjon
    SETTYPE_PARAM = Geometry Name
    SET -> GeometryPropertySetter_SET
Note: Slår sammen linjesegmenter
LineJoiner
    CONSIDER_NODE_ELEVATION = no
    PRESERVE = no
    LINES_AS_SEGMENTS = No
    TOPOLOGY = End noded
    BREAK = no
    GROUP_BREAK = no
    GROUP_BY = identifikasjon.Identifikasjon.lokalId
    LINE -> FeatureMerger_2 [REQUESTOR]
FeatureMerger_2
    ATTR_ACCUM_MODE = Merge Supplier
    JOIN_KEYS = @Value(identifikasjon.Identifikasjon.lokalId) @Value(identifikasjon.Identifikasjon.lokalId) AUTO
    PROCESS_DUPS = No
    MERGE_TYPE = Attributes Only
    SUPPLIERS_FIRST = No
    ATTR_CONFLICT_RES = Use Requestor
    IGNORE_NULLS = No
    MERGED -> GeometryPropertySetter_4
GeometryPropertySetter_4
    OVERWRITE_CHOICE = Yes
    GEOM_NAME_FIELD = senterlinje
    SETTYPE_PARAM = Geometry Name
    SET -> GeometryPropertySetter_SET
GeometryPropertySetter_3
    OVERWRITE_CHOICE = Yes
    GEOM_NAME_FIELD = område
    SETTYPE_PARAM = Geometry Name
    SET -> GeometryPropertySetter_3_SET
GeometryPropertySetter_3_SET: Junction
    -> GeometryPropertySetter_SET
