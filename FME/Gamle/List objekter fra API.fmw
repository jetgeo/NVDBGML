FME workspace List objekter fra API.fmw

Parameters:
- xfmap_api = $(FME_MF_DIR)API_Mapping.xmp   # xfMap for API-mapping
- coordsys = EPSG:25833   # Koordinatsystem
- DestDataset_CSV = C:\Users\knjetl\Desktop   # Destination CSV (Comma Separated Value) Folder

Writers:
- CSV_1: CSV to $(DestDataset_CSV)

Creator
    NUM = 1
    GEOMTYPE = Geometry Object
    CREATED -> HTTPFetcher_2
Note: Henter objekter fra NVDB-API
HTTPFetcher_2
    AUTH_METHOD = Basic
    FOLLOW_REDIRECTS = Yes
    REQUEST_HEADER:
      GET /vegobjekter HTTP/1.1
      Accept: application/vnd.vegvesen.nvdb-v1+xml
    TARGET_URL = https://www.vegvesen.no/nvdb/api/sok?kriterie={"lokasjon":{"vegreferanse":["FV330"],"bbox":"249480,6765663,265736,6775114"},"objektTyper":[{"id":62,"filter":[{"type":"Geometri,%20linje","operator":"!=","verdi":null}]}]}
    USE_COOKIES = No
    ERROR_ATTR = _error
    RESPONSE_HEADER_LIST_ATTR = _headers
    PROXY_AUTH_METHOD = Basic
    SAVE_FILE = No
    TARGET_ATTR = _url_contents
    STATUS_CODE_ATTR = _http_status_code
    VERIFY_SSL_CERTIFICATES = Yes
    -> XMLFeatureMapper
Note: Tolker XML
XMLFeatureMapper
    XML_SOURCE_NAME = _xml_source_
    SINGLE_XFMAP = $(xfmap_api)
    XML_INPUT_TYPE = Attribute with XML document
    CONFIGURATION_TYPE = Single xfMap file
    FEATURE_TYPE_ATTR = fme_feature_type
    MERGE_ATTRS = Yes
    FEATURE_COUNT_PER_XML = _xml_feature_count_
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt assosiasjon{}.typeId assosiasjon{}.uri
    ATTRIBUTE_XML = _url_contents
    MAPPED -> GeometryReplacer
Note: Tildeler geometri
GeometryReplacer
    KIND_LONG = OGC Well Known Text
    OGC_WKT_PRECISION_DISPLAY = 64-bit
    REMOVE_ATTRIBUTE = Yes
    SOURCE = @Value(geometriUtm33)
    -> CoordinateSystemSetter
CoordinateSystemSetter
    COORDSYS = $(coordsys)
    -> CoordinateSystemSetter_Output
    -> Objekter (writer CSV_1)
CoordinateSystemSetter_Output: Inspector
Objekter (writer CSV_1)
    attributes: NVDB_ID auto
