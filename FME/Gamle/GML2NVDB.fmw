FME workspace GML2NVDB.fmw

Parameters:
- SourceDataset_GML = C:\DATA\Standardisering\NVDBGML\GML\InnmålteStikkrennerMGD.gml   # Source Geography Markup Language (GML) File(s)

Readers:
- GML_1: GML from $(SourceDataset_GML)

Stikkrenne (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer, bruksområde xml_buffer,
      senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
    -> SchemaMapper
    -> GML_Original
NVDB: Inspector [off]
    TACKATTRS = fme_feature_type
Reprojector
    SOURCE = Read from feature
    RASTER_CELL_SIZE = Preserve Cells
    DEST = EPSG:25833
    INTERPOLATION_TYPE_NAME = Nearest Neighbor
    REPROJECTED -> TimeStamper
TimeStamper
    FMT = XML Date (^Y-^m-^d)
    TIME_ATTR = _timestamp
    -> CoordinateExtractor
WithLR: Inspector
GML_Original: Inspector [off]
    TACKATTRS = fme_feature_type

Bookmark: Mapping til NVDB-IDer
Note: Mapper objekttypenavn til VOT-ID, vha mappingtabell ftMapping
SchemaMapper
    TABLE = CSV
    CSV__FIELD_NAMES_AFTER_HEADER = no
    CSV__SCHEMA = number,3,0,char,50,
    CSV__STRIP_QUOTES = yes
    FORMAT = CSV
    IDXDESTATTR = fme_feature_type
    CSV__DUPLICATE_DELIMS = no
    ROW_ID_ATTR = _schemamapper_row_ids
    IDXDESTCOL = ftid
    CSV__IN_SEPARATOR = ;
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__ALLOW_SPACES_IN_COLUMN_NAMES = yes
    CSV__SCHEMA_WITH_COL_NAMES = ftid,number,3,0,name,char,50,
    CSV__GROUP_BY_DATASET = no
    IDXSOURCECOL = name
    CSV__SKIP_LINES = 1
    CSV_SCAN_MAX_FEATURES = 1000
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__IN_FIELD_NAMES = YES
    DATASET = C:\DATA\Standardisering\NVDBGML\tmp\ftMapping.csv
    IDXSOURCEATTR = fme_feature_type
    CSV__SKIP_FOOTER = 0
    MAPPED -> AttributeExposer
AttributeExposer
    ATTR_LIST = fme_feature_type
    -> SchemaMapper_2
Note: Mapper egenskapsnavn til ET-ID, vha mappingtabell ptMapping
SchemaMapper_2
    TABLE = CSV
    CSV__FIELD_NAMES_AFTER_HEADER = no
    CSV__SCHEMA = char,17,,number,3,0,number,6,0,char,21,
    CSV__STRIP_QUOTES = yes
    FORMAT = CSV
    IDXDESTATTR = fme_feature_type
    MATCH_ATTRS = ft_attr ftid
    CSV__DUPLICATE_DELIMS = no
    ROW_ID_ATTR = _schemamapper_row_ids
    IDXDESTCOL = ""
    MAP_ATTRS = name ptid $(FME_ASC_16)
    CSV__IN_SEPARATOR = ;
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__ALLOW_SPACES_IN_COLUMN_NAMES = yes
    CSV__SCHEMA_WITH_COL_NAMES = ft_attr,char,17,,ftid,number,3,0,ptid,number,6,0,name,char,21,
    CSV__GROUP_BY_DATASET = no
    IDXSOURCECOL = ""
    CSV__SKIP_LINES = 1
    CSV_SCAN_MAX_FEATURES = 1000
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__IN_FIELD_NAMES = YES
    DATASET = C:\DATA\Standardisering\NVDBGML\tmp\ptMapping.csv
    IDXSOURCEATTR = fme_feature_type
    CSV__SKIP_FOOTER = 0
    MAPPED -> SchemaMapper_3
Note: Mapper egenskapsverdier til TV-ID, vha mappingtabell enMapping
SchemaMapper_3
    TABLE = CSV
    CSV__FIELD_NAMES_AFTER_HEADER = no
    CSV__SCHEMA = number,6,0,number,6,0,char,31,
    CSV__STRIP_QUOTES = yes
    FORMAT = CSV
    IDXDESTATTR = fme_feature_type
    MATCH_ATTRS = ptid name
    CSV__DUPLICATE_DELIMS = no
    ROW_ID_ATTR = _schemamapper_row_ids
    IDXDESTCOL = ""
    MAP_ATTRS = """""" ptid enid
    CSV__IN_SEPARATOR = ;
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__ALLOW_SPACES_IN_COLUMN_NAMES = yes
    CSV__SCHEMA_WITH_COL_NAMES = ptid,number,6,0,enid,number,6,0,name,char,31,
    CSV__GROUP_BY_DATASET = no
    IDXSOURCECOL = ""
    CSV__SKIP_LINES = 1
    CSV_SCAN_MAX_FEATURES = 1000
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name\"%%\"Filter\"%\"STRING_ENCODED _FILTER_REGEX \"%%\"Invert Filter\"%\"CHECKBOX _FILTER_UNMATCHED yes%no\"%no"
    CSV__IN_FIELD_NAMES = YES
    DATASET = C:\DATA\Standardisering\NVDBGML\tmp\enMapping.csv
    IDXSOURCEATTR = fme_feature_type
    CSV__SKIP_FOOTER = 0
    MAPPED -> NVDB
    MAPPED -> Reprojector

Bookmark: Lineær posisjon - Må tilpasses: Hvordan finne ut om objekttypen skal ha strekning eller punkt-LR?
Note: Startkoordinater
CoordinateExtractor
    Y_ATTR = _yStart
    X_ATTR = _xStart
    Z_DEFAULT = -9999
    IND = 0
    Z_ATTR = _zStart
    -> AttributeCreator
AttributeCreator
    ATTR_LIST = httpReq,http://multirit.triona.se/visveginfo/RoadInfoService/GetRoadReferenceForLocation?easting=@Value(_xStart)&northing=@Value(_yStart)&coordinateSystem=UTM33&viewdate=@Value(_timestamp)&bufferMeters=10
    -> HTTPCaller
HTTPCaller
    TARGET_URL = @Value(httpReq)
    CONNECTION_TIMEOUT_LENGTH = 60
    TRANSFER_TIMEOUT_LENGTH = 90
    STATUS_CODE_ATTR = _http_status_code
    SAVE_FILE = Attribute
    ERROR_ATTR = _error
    VERIFY_SSL_CERTIFICATES = Yes
    TARGET_ATTR_ENCODING = auto-detect
    USE_COOKIES = No
    RESPONSE_HEADER_LIST_ATTR = _headers
    FOLLOW_REDIRECTS = Yes
    TARGET_ATTR = _response_body
    HTTP_METHOD = GET
    -> XMLFlattener
XMLFlattener
    EMBEDDED_EXPRESSIONS = ReflinkOID Measure
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = ReflinkOID Measure
    XML_SOURCE_TYPE = Attribute with XML document
    ATTRIBUTE_XML = _response_body
    -> BulkAttributeRenamer
BulkAttributeRenamer
    ATTRLIST = Measure ReflinkOID
    REPLACE_STR = Start
    PATTERN_ACTION_DISP = Add String Prefix
    ATTRCHOICE = Selected Attributes
    -> CoordinateExtractor_2
Note: Sluttkoordinater
CoordinateExtractor_2
    Y_ATTR = _yEnd
    X_ATTR = _xEnd
    Z_DEFAULT = -9999
    IND = 0
    Z_ATTR = _zEnd
    -> AttributeCreator_2
AttributeCreator_2
    ATTR_LIST = httpReq,http://multirit.triona.se/visveginfo/RoadInfoService/GetRoadReferenceForLocation?easting=@Value(_xEnd)&northing=@Value(_yEnd)&coordinateSystem=UTM33&viewdate=@Value(_timestamp)&bufferMeters=10
    -> HTTPCaller_2
HTTPCaller_2
    TARGET_URL = @Value(httpReq)
    CONNECTION_TIMEOUT_LENGTH = 60
    TRANSFER_TIMEOUT_LENGTH = 90
    STATUS_CODE_ATTR = _http_status_code
    SAVE_FILE = Attribute
    ERROR_ATTR = _error
    VERIFY_SSL_CERTIFICATES = Yes
    TARGET_ATTR_ENCODING = auto-detect
    USE_COOKIES = No
    RESPONSE_HEADER_LIST_ATTR = _headers
    FOLLOW_REDIRECTS = Yes
    TARGET_ATTR = _response_body
    HTTP_METHOD = GET
    -> XMLFlattener_2
XMLFlattener_2
    EMBEDDED_EXPRESSIONS = ReflinkOID Measure
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = ReflinkOID Measure
    XML_SOURCE_TYPE = Attribute with XML document
    ATTRIBUTE_XML = _response_body
    -> BulkAttributeRenamer_2
BulkAttributeRenamer_2
    ATTRLIST = Measure ReflinkOID
    REPLACE_STR = End
    PATTERN_ACTION_DISP = Add String Prefix
    ATTRCHOICE = Selected Attributes
    -> TestFilter
TestFilter
    DEFAULT_VALUE = Ulik lenke
    TEST_LIST = BOOL_OP,OR,COMPOSITE_TEST,<Unused>,TEST_CLAUSE,"TEST @Value(StartReflinkOID) = @Value(EndReflinkOID)",Samme lenke
    Samme lenke -> AttributeCreator_3
    Ulik lenke -> AttributeCreator_4
AttributeCreator_3
    ATTR_LIST = lokasjon.lenkeId,@Value(StartReflinkOID),lokasjon.posisjon,@Evaluate((@Value(StartMeasure)+@Value(EndMeasure))/2)
    -> WithLR
AttributeCreator_4
    ATTR_LIST = lokasjon.lenkeId,@Value(StartReflinkOID),lokasjon.posisjon,@Value(StartMeasure)
    -> WithLR
