FME workspace Skred.fmw

Parameters:
- gmlName = Bomstasjon   # GML file and schema name
- ftID = 45   # NVDB feature type ID
- xsdFolder = C:\DATA\Standardisering\NVDB-GML\XSD   # XSD Main folder
- gmlFolder = C:\DATA\Standardisering\NVDB-GML\GML   # Output GML folder
- gmlNamespace = http://www.jetlundweb.no/geomatikk/GML/NVDB   # GML Namespace
- xfmap_api = $(FME_MF_DIR)API_Mapping.xmp   # xfMap for API-mapping
- xsd_xfmap = $(FME_MF_DIR)NVDB_GML_SchemaMapper.xmp   # XSD xfMap File
- coordsys = EPSG:25833   # Koordinatsystem
- namespace = vegvesen.no.nvdb   # Attribute Value
- xsdLocalComplete:   # Python Script
      xsdLC = FME_MacroValues['xsdFolder'] + '\\' + FME_MacroValues['gmlName'] + '.xsd'
      #Debug
      #print xsdLC
      return xsdLC
- gmlComplete:   # Python Script
      gmlLC = FME_MacroValues['gmlFolder'] + '\\' + FME_MacroValues['gmlName'] + '.gml'
      #Debug
      #print gmlLC
      return gmlLC

Writers:
- GML_1: GML to $(gmlComplete)

Creator
    NUM = 1
    GEOMTYPE = Geometry Object
    CREATED -> AttributeCreator
AttributeCreator
    NUM_PRIOR_FEATURES = 0
    ATTR_LIST = _api,https://www.vegvesen.no/nvdb/api/sok?kriterie={objektTyper:[{id:$(ftID),antall:10}]},_gmlFeatureType,$(gmlName)
    NUM_SUBSEQUENT_FEATURES = 0
    -> NVDBAPI2GML
NVDBAPI2GML
    namespace = $(namespace)
    apiString = @Value(_api)
    coordsys = $(coordsys)
    xsd_xfmap = $(xsd_xfmap)
    xfmap_api = $(xfmap_api)
    xsd = $(xsdLocalComplete)
    -> Vegobjekttype (writer GML_1)
Vegobjekttype (writer GML_1)
    attributes: _creation_instance xml_char(200), _api xml_char(200), _gmlFeatureType xml_char(200), _headers{}.name xml_char(200), _headers{}.value xml_char(200), _error xml_char(200), _http_status_code xml_char(200), _url_contents xml_char(200), egengeometri xml_char(200), geometriUtm33 xml_char(200), _xml_feature_count_ xml_char(200), _xml_source_ xml_char(200), _schemamapper_row_ids xml_char(200), prosesshistorie xml_buffer, identifikasjon.Identifikasjon.lokalId xml_buffer, identifikasjon.Identifikasjon.navnerom xml_buffer

FME custom transformer NVDBAPI2GML

Parameters:
- xsd = C:\DATA\Standardisering\NVDB-GML\XSD\NVDBStikkrenneKomplett.xsd   # Application Schema
- apiString = @Value(_api)   # Tekst med kall til API
- xfmap_api = $(FME_MF_DIR)API_Mapping.xmp   # xfMap for API-mapping
- xsd_xfmap = $(FME_MF_DIR)NVDB_GML_SchemaMapper.xmp   # XSD xfMap File
- namespace = vegvesen.no.nvdb   # Attribute Value
- coordsys = EPSG:25833   # Koordinatsystem

Input (input)
    -> HTTPFetcher_2
Note: Henter objekter fra NVDB-API
HTTPFetcher_2
    FOLLOW_REDIRECTS = Yes
    REQUEST_HEADER:
      GET /vegobjekter HTTP/1.1
      Accept: application/vnd.vegvesen.nvdb-v1+xml
    USE_COOKIES = No
    SAVE_FILE = No
    RESPONSE_HEADER_LIST_ATTR = _headers
    VERIFY_SSL_CERTIFICATES = Yes
    AUTH_METHOD = Basic
    ERROR_ATTR = _error
    TARGET_ATTR = _url_contents
    STATUS_CODE_ATTR = _http_status_code
    TARGET_URL = @Value(_api)
    PROXY_AUTH_METHOD = Basic
    -> XMLFeatureMapper
Note: Tolker XML
XMLFeatureMapper
    CONFIGURATION_TYPE = Single xfMap file
    ATTRIBUTE_XML = _url_contents
    MERGE_ATTRS = Yes
    FEATURE_COUNT_PER_XML = _xml_feature_count_
    FEATURE_TYPE_ATTR = fme_feature_type
    XML_SOURCE_NAME = _xml_source_
    SINGLE_XFMAP = $(xfmap_api)
    NEW_ATTRIBUTES = egengeometri geometriUtm33
    XML_INPUT_TYPE = Attribute with XML document
    MAPPED -> GeometryReplacer
Note: Tildeler geometri
GeometryReplacer
    REMOVE_ATTRIBUTE = Yes
    KIND_LONG = OGC Well Known Text
    SOURCE = @Value(geometriUtm33)
    -> CoordinateSystemSetter
CoordinateSystemSetter
    COORDSYS = $(coordsys)
    -> SchemaMapper
Note: Mapper egenskapsnavn til GML, vha applikasjonsskjemaet
SchemaMapper
    XML_CLIP_TO_ENVELOPE = NO
    FORMAT = XML
    IDXDESTATTR = fme_feature_type
    IDXSOURCEATTR = fme_feature_type
    MAP_ATTRS = NVDB_ID name """"""
    XML_XFMAP = $(xsd_xfmap)
    DATASET = $(xsd)
    XML_USE_HTTP_AUTH = NO
    ROW_ID_ATTR = _schemamapper_row_ids
    XML_FILE_TYPE = xfMap
    IDXSOURCECOL = ""
    IDXDESTCOL = ""
    XML_CONTINUE_ON_GEOM_ERROR = yes
    TABLE = element
    MAPPED -> NullAttributeMapper
NullAttributeMapper
    ATTRCHOICE = All Attributes
    SOURCE_ATTR_VAL = Empty Null
    NULL_TREATMENT = Missing
    -> AttributeValueMapper_2
AttributeValueMapper_2
    LUT = true,Geometri: Egengeometri fra NVDB
    DIRECTION = Forward (Source To Destination)
    DEFAULT_VALUE = Geometri: Generert fra lineære referanser til vegnett i NVDB
    VAL_ATTR = prosesshistorie
    SRC = egengeometri
    -> GeometryFilter
AttributeExposer
    ATTR_LIST = NVDB_ID
    -> AttributeRenamer_3
Note: ID
AttributeRenamer_3
    ATTR_LIST = NVDB_ID,identifikasjon.Identifikasjon.lokalId,"","",identifikasjon.Identifikasjon.navnerom,$(namespace)
    -> Output (output)
Output (output)

Bookmark: Definerer geometriegenskaper
GeometryFilter
    GEOM_PORT_NAMES = Point Line Area
    BREAK_AGG = No
    POINT -> GeometryPropertySetter
    LINE -> GeometryPropertySetter_2
    AREA -> GeometryPropertySetter_3
GeometryPropertySetter
    GEOM_NAME_FIELD = posisjon
    SETTYPE_PARAM = Geometry Name
    OVERWRITE_CHOICE = Yes
    SET -> AttributeExposer
GeometryPropertySetter_2
    GEOM_NAME_FIELD = senterlinje
    SETTYPE_PARAM = Geometry Name
    OVERWRITE_CHOICE = Yes
    SET -> AttributeExposer
GeometryPropertySetter_3
    GEOM_NAME_FIELD = område
    SETTYPE_PARAM = Geometry Name
    OVERWRITE_CHOICE = Yes
    SET -> AttributeExposer
