FME workspace TrimbleStikkrenner.fmw

Parameters:
- xsd = C:\DATA\Standardisering\NVDB-GML\XSD\Stikkrenne.xsd   # Application Schema
- schemalocation = http://www.jetlundweb.no/geomatikk/GML/NIFS http://www.jetlundweb.no/geomatikk/GML/NIFS/Stikkrenne.xsd   # Target xsi:schemaLocation URL
- DestDataset_GML = C:\DATA\Standardisering\NVDB-GML\GML\InnmålteStikkrennerMGD.gml   # Destination Geography Markup Language (GML) File
- SourceDataset_GML = C:\DATA\NIFS\Data\stikkrennetest3.xml   # Source Geography Markup Language (GML) File(s)

Readers:
- GML_1: GML from $(SourceDataset_GML)

Writers:
- GML_2: GML to $(DestDataset_GML)

Stikkrenne (reader GML_1)
    attributes: gml_parent_id xml_buffer, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer,
      bruksområde xml_buffer, senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
    -> DateFormatter_3
DateFormatter_3
    SRCFMT = Unknown - Automatic Detection
    INVALID_DATE_VALUE = _FME_NO_OP_
    DATE_ATTR = datafangstdato,endringsflagg.Endringsflagg.tidspunktEndring
    FMT = %Y"-"%m"-"%d
    -> NullAttributeMapper
NullAttributeMapper
    NULL_TREATMENT = Missing
    SOURCE_ATTR_VAL = Empty Null
    OTHER_VALUE = ?
    ATTRCHOICE = All Attributes
    -> NullAttributeMapper_2
NullAttributeMapper_2
    NULL_TREATMENT = Missing
    OTHER_VALUE = T00:00:00
    ATTRCHOICE = All Attributes
    -> AttributeValueMapper
AttributeValueMapper
    DIRECTION = Forward (Source To Destination)
    VAL_ATTR = harInnløpsrist
    LUT = false,Nei,true,Ja
    SRC = harInnløpsrist
    -> NullAttributeMapper_3
NullAttributeMapper_3
    NULL_TREATMENT = New Value
    NEW_VALUE = N
    ATTRLIST = endringsflagg.Endringsflagg.typeEndring
    SOURCE_ATTR_VAL = Null Empty "Missing (Selected Attributes Only)"
    ATTRCHOICE = Selected Attributes
    -> Stikkrenne (writer GML_2)
Stikkrenne (writer GML_2)
    attributes: gml_parent_id xml_buffer, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer,
      bruksområde xml_buffer, senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
