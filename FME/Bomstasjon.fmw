FME workspace Bomstasjon.fmw

Parameters:
- xsd = C:\DATA\Standardisering\NVDB-GML\XSD\Bomstasjon.xsd   # Application Schema
- schemalocation = http://www.jetlundweb.no/geomatikk/GML/NVDB http://www.jetlundweb.no/geomatikk/GML/NVDB/Bomstasjon.xsd   # Target xsi:schemaLocation URL
- DestDataset_GML = C:\DATA\Standardisering\NVDB-GML\GML\Bomstasjon.gml   # Destination Geography Markup Language (GML) File
- xfmap_api = $(FME_MF_DIR)API_Mapping.xmp   # xfMap for API-mapping
- xsd_xfmap = $(FME_MF_DIR)NVDB_GML_SchemaMapper.xmp   # XSD xfMap File
- coordsys = EPSG:25833   # Koordinatsystem
- namespace = vegvesen.no.nvdb   # Attribute Value

Writers:
- GML_1: GML to $(DestDataset_GML)

Creator
    NUM = 1
    GEOMTYPE = Geometry Object
    CREATED -> AttributeCreator
AttributeCreator
    ATTR_LIST = _api,https://www.vegvesen.no/nvdb/api/vegobjekter/45?rows=10000
    NUM_SUBSEQUENT_FEATURES = 0
    NUM_PRIOR_FEATURES = 0
    -> NVDBAPI2GML
NVDBAPI2GML
    coordsys = $(coordsys)
    namespace = $(namespace)
    apiString = @Value(_api)
    xsd = $(xsd)
    xsd_xfmap = $(xsd_xfmap)
    xfmap_api = $(xfmap_api)
    -> Bomstasjon (writer GML_1)
Bomstasjon (writer GML_1)
    attributes: gml_parent_id xml_buffer, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.synbarhet.codeSpace xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, høydereferanse xml_buffer, høydereferanse.codeSpace xml_buffer, vegident.Vegident.vegkategori xml_buffer, vegident.Vegident.vegkategori.codeSpace xml_buffer, vegident.Vegident.vegstatus xml_buffer, vegident.Vegident.vegstatus.codeSpace xml_buffer, vegident.Vegident.vegnummer xml_int64, vegparsell.Vegparsell.hovedParsell xml_int64, vegparsell.Vegparsell.veglenkeMeterFra xml_int64, vegparsell.Vegparsell.veglenkeMeterTil xml_int64, sideposisjon xml_buffer, bomstasjonstype xml_buffer, navnBompengeanlegg xml_buffer,
      navnBomstasjon xml_buffer, bomstasjonId xml_int64, vedtattTilÅr xml_int64, rushtidstakstLitenBil xml_real64, innkrevningsretning xml_buffer, bompengeanleggId xml_int64, takstLitenBil xml_real64, takstStorBil xml_real64, rushtidsavgift xml_buffer, rushtidstakstStorBil xml_real64, rushtidMorgenFra xml_buffer, rushtidMorgenTil xml_buffer, rushtidEttermiddagFra xml_buffer, rushtidEttermiddagTil xml_buffer, timesregel xml_buffer, gratisGjennomkjøringVedHCBrikke xml_buffer, byggeår xml_int64, eier xml_buffer, vedlikeholdsansvarlig xml_buffer, posisjon xml_geometry, lineærPosisjon.LineærPosisjonPunkt.lineærreferanseMetode xml_buffer, lineærPosisjon.LineærPosisjonPunkt.felt xml_buffer, lineærPosisjon.LineærPosisjonPunkt.avstandSide xml_real64, lineærPosisjon.LineærPosisjonPunkt.lineærtObjektIdentifikasjon.nilReason xml_buffer, lineærPosisjon.LineærPosisjonPunkt.lineærtObjektIdentifikasjon.gml_remoteSchema xml_buffer, lineærPosisjon.LineærPosisjonPunkt.lineærtObjektIdentifikasjon.xlink_href xml_buffer, lineærPosisjon.LineærPosisjonPunkt.lineærtObjektIdentifikasjon.owns xml_boolean, lineærPosisjon.LineærPosisjonPunkt.posisjon xml_real64

FME custom transformer NVDBAPI2GML

Parameters:
- xsd = C:\DATA\Standardisering\NVDB-GML\XSD\NVDBStikkrenneKomplett.xsd   # Application Schema
- apiString = @Value(_api)   # Tekst med kall til API
- xfmap_api = $(FME_MF_DIR)API_Mapping.xmp   # xfMap for API-mapping
- xsd_xfmap = $(FME_MF_DIR)NVDB_GML_SchemaMapper.xmp   # XSD xfMap File
- namespace = vegvesen.no.nvdb   # Attribute Value
- coordsys = EPSG:25833   # Koordinatsystem

Input (input)
    -> HTTPFetcher_2
Note: Henter objekter fra NVDB-API
HTTPFetcher_2
    USE_COOKIES = No
    PROXY_AUTH_METHOD = Basic
    REQUEST_HEADER:
      GET /vegobjekter HTTP/1.1
      Accept: application/vnd.vegvesen.nvdb-v1+xml
    TARGET_URL = @Value(_api)
    SAVE_FILE = No
    RESPONSE_HEADER_LIST_ATTR = _headers
    VERIFY_SSL_CERTIFICATES = Yes
    TARGET_ATTR = _url_contents
    AUTH_METHOD = Basic
    ERROR_ATTR = _error
    STATUS_CODE_ATTR = _http_status_code
    FOLLOW_REDIRECTS = Yes
    -> XMLFeatureMapper
Note: Tolker XML
XMLFeatureMapper
    XML_INPUT_TYPE = Attribute with XML document
    FEATURE_TYPE_ATTR = fme_feature_type
    MERGE_ATTRS = Yes
    SINGLE_XFMAP = $(xfmap_api)
    FEATURE_COUNT_PER_XML = _xml_feature_count_
    CONFIGURATION_TYPE = Single xfMap file
    XML_SOURCE_NAME = _xml_source_
    NEW_ATTRIBUTES = egengeometri geometriUtm33
    ATTRIBUTE_XML = _url_contents
    MAPPED -> GeometryReplacer
Note: Tildeler geometri
GeometryReplacer
    KIND_LONG = OGC Well Known Text
    SOURCE = @Value(geometriUtm33)
    REMOVE_ATTRIBUTE = Yes
    -> CoordinateSystemSetter
CoordinateSystemSetter
    COORDSYS = $(coordsys)
    -> SchemaMapper
Note: Mapper egenskapsnavn til GML, vha applikasjonsskjemaet
SchemaMapper
    IDXDESTCOL = ""
    ROW_ID_ATTR = _schemamapper_row_ids
    XML_CLIP_TO_ENVELOPE = NO
    IDXSOURCEATTR = fme_feature_type
    FORMAT = XML
    XML_USE_HTTP_AUTH = NO
    IDXSOURCECOL = ""
    MAP_ATTRS = NVDB_ID name """"""
    XML_FILE_TYPE = xfMap
    XML_XFMAP = $(xsd_xfmap)
    XML_CONTINUE_ON_GEOM_ERROR = yes
    DATASET = $(xsd)
    TABLE = element
    IDXDESTATTR = fme_feature_type
    MAPPED -> NullAttributeMapper
NullAttributeMapper
    ATTRCHOICE = All Attributes
    NULL_TREATMENT = Missing
    SOURCE_ATTR_VAL = Empty Null
    -> AttributeValueMapper_2
AttributeValueMapper_2
    VAL_ATTR = prosesshistorie
    DEFAULT_VALUE = Geometri: Generert fra lineære referanser til vegnett i NVDB
    DIRECTION = Forward (Source To Destination)
    LUT = true,Geometri: Egengeometri fra NVDB
    SRC = egengeometri
    -> GeometryFilter
AttributeExposer
    ATTR_LIST = NVDB_ID
    -> AttributeRenamer_3
Note: ID
AttributeRenamer_3
    ATTR_LIST = NVDB_ID,identifikasjon.Identifikasjon.lokalId,"","",identifikasjon.Identifikasjon.navnerom,$(namespace)
    -> Output (output)
Output (output)

Bookmark: Definerer geometriegenskaper
GeometryFilter
    GEOM_PORT_NAMES = Point Line Area
    BREAK_AGG = No
    POINT -> GeometryPropertySetter
    LINE -> GeometryPropertySetter_2
    AREA -> GeometryPropertySetter_3
GeometryPropertySetter
    GEOM_NAME_FIELD = posisjon
    SETTYPE_PARAM = Geometry Name
    OVERWRITE_CHOICE = Yes
    SET -> AttributeExposer
GeometryPropertySetter_2
    GEOM_NAME_FIELD = senterlinje
    SETTYPE_PARAM = Geometry Name
    OVERWRITE_CHOICE = Yes
    SET -> AttributeExposer
GeometryPropertySetter_3
    GEOM_NAME_FIELD = område
    SETTYPE_PARAM = Geometry Name
    OVERWRITE_CHOICE = Yes
    SET -> AttributeExposer
