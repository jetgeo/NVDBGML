FME workspace NVDBAPI2GML_feilsøk.fmw

Parameters:
- gmlName = Drenering   # GML file and schema name
- ftID = 78   # NVDB feature type ID
- Kommuner = 516,519,520   # komm
- xsdFolder = C:\DATA\Standardisering\NVDBGML\XSD   # XSD Main folder
- gmlFolder = C:\DATA\Standardisering\NVDBGML\GML   # Output GML folder
- gmlNamespace = https://raw.githubusercontent.com/jetgeo/NVDBGML/master/XSD   # GML Namespace
- xfmap_api = $(FME_MF_DIR)API_Mapping.xmp   # xfMap for API-mapping
- xfmap_xsd = $(FME_MF_DIR)NVDB_GML_SchemaMapper.xmp   # xfMap for XSD
- coordsys = EPSG:25833   # Koordinatsystem
- namespace = vegvesen.no.nvdb   # Attribute Value
- xsdLocalComplete:   # Python Script
      xsdLC = FME_MacroValues['xsdFolder'] + '\\' + FME_MacroValues['gmlName'] + '.xsd'
      #Debug
      #print xsdLC
      return xsdLC
- gmlComplete:   # Python Script
      gmlLC = FME_MacroValues['gmlFolder'] + '\\' + FME_MacroValues['gmlName'] + '.gml'
      #Debug
      #print gmlLC
      return gmlLC
- maxFeatures = 10000   # Maximal number of features

Writers:
- GML_1: GML to $(gmlComplete)

Creator
    NUM = 1
    GEOMTYPE = Geometry Object
    CREATED -> AttributeCreator_3
AttributeCreator_3
    ATTR_LIST = ftID,$(ftID)
    -> AttributeSplitter
AttributeSplitter
    DROP_EMPTY_PARTS = No
    TRIM_OPTION = Both
    LIST_NAME = _ftID
    ATTR_NAME = ftID
    DELIMITER = ,
    -> ListExploder
ListExploder
    INDEX_ATTR = _element_index
    ATTR_CONFLICT_RES = Use Original
    LIST_ATTR = _ftID{}
    ATTR_ACCUM_MODE = Merge Incoming List
    LIST_FOUND -> AttributeCreator
    LIST_FOUND -> AttributeCreator_2
    NOT_FOUND -> AttributeCreator_2
    NOT_FOUND -> AttributeCreator
Note: Kunne hente alle objekttyper fra et gitt applikasjonsskjema? / - Lese alle objekttyper i et applikasjonsskjema, med ID, og sende disse til API
Note: AttributeCreator [AttributeCreator:6] / DISABLED / Number of Prior Features: 0 / Number of Subsequent Features: 0 / _api = https://www.vegvesen.no/nvdb/api/sok?kriterie={objektTyper:[{id:@Value(_ftID),antall:$(maxFeatures)}]} / _gmlFeatureType = $(gmlName) / Version: 6 / Last Parameter Edit: Build 15479
AttributeCreator [off]
    NUM_PRIOR_FEATURES = 0
    NUM_SUBSEQUENT_FEATURES = 0
    ATTR_LIST = _api,https://www.vegvesen.no/nvdb/api/sok?kriterie={objektTyper:[{id:@Value(_ftID),antall:$(maxFeatures)}]},_gmlFeatureType,$(gmlName)
    -> NVDBAPI2GML
Note: AttributeCreator_2 [AttributeCreator:6] / Number of Prior Features: 0 / Number of Subsequent Features: 0 / _api = https://www.vegvesen.no/nvdb/api/sok?kriterie={lokasjon:{kommune: [$(Kommuner)]},objektTyper:[{id:@Value(_ftID),antall:$(maxFeatures)}]} / Version: 6 / Last Parameter Edit: Build 15479
AttributeCreator_2
    NUM_PRIOR_FEATURES = 0
    NUM_SUBSEQUENT_FEATURES = 0
    ATTR_LIST = _api,https://www.vegvesen.no/nvdb/api/sok?kriterie={lokasjon:{kommune: [$(Kommuner)]},objektTyper:[{id:@Value(_ftID),antall:$(maxFeatures)}]}
    -> NVDBAPI2GML
NVDBAPI2GML
    mfPT:
      mfLC = FME_MacroValues['mfLocalPrefix']+ '_ptMapping.csv'
      return mfLC
    xfmap_xsd = $(xfmap_xsd)
    coordsys = $(coordsys)
    xsd = $(xsdLocalComplete)
    namespace = $(namespace)
    apiString = @Value(_api)
    mfLocalPrefix = $(xsdFolder)\$(gmlName)
    xfmap_api = $(xfmap_api)
    mfFT:
      mfLC = FME_MacroValues['mfLocalPrefix']+ '_ftMapping.csv'
      return mfLC
    -> Vegobjekttype (writer GML_1)
Vegobjekttype (writer GML_1)
    attributes: _creation_instance xml_char(200), ftID xml_char(200), _ftID xml_char(200), _element_index xml_char(200), _api xml_char(200), _gmlFeatureType xml_char(200), _headers{}.name xml_char(200), _headers{}.value xml_char(200), _error xml_char(200), _http_status_code xml_char(200), _url_contents xml_char(200), egengeometri xml_char(200), vegreferanse{}.vegkategori xml_char(200), vegreferanse{}.vegnummer xml_char(200), vegreferanse{}.vegstatus xml_char(200), vegreferanse{}.hovedParsell xml_char(200), vegreferanse{}.veglenkeMeterFra xml_char(200), vegreferanse{}.veglenkeMeterTil xml_char(200), _xml_feature_count_ xml_char(200), _xml_source_ xml_char(200), _schemamapper_row_ids xml_char(200), prosesshistorie xml_char(200), identifikasjon.Identifikasjon.lokalId xml_buffer, identifikasjon.Identifikasjon.navnerom xml_buffer, lineærPosisjon.LineærPosisjonPunkt.lineærtObjektIdentifikasjon.Identifikasjon.lokalId xml_char(200), lineærPosisjon.LineærPosisjonPunkt.posisjon xml_char(200), lineærPosisjon.LineærPosisjonPunkt.tilPosisjon xml_char(200), lineærPosisjon.LineærPosisjonPunkt.felt xml_char(200), _element_count xml_char(200), lineærPosisjon.LineærPosisjonPunkt.lineærtObjektIdentifikasjon.Identifikasjon.navnerom xml_char(200),
      lineærPosisjon{}.LineærPosisjonStrekning.lineærtObjektIdentifikasjon.Identifikasjon.lokalId xml_char(200), lineærPosisjon{}.LineærPosisjonStrekning.fraPosisjon xml_char(200), lineærPosisjon{}.LineærPosisjonStrekning.tilPosisjon xml_char(200), lineærPosisjon{}.LineærPosisjonStrekning.felt xml_char(200), lineærPosisjon{}.identifikasjon.Identifikasjon.lokalId xml_char(200), lineærPosisjon{}._element_count xml_char(200), lineærPosisjon{}._element_index xml_char(200), lineærPosisjon{}.LineærPosisjonStrekning.lineærtObjektIdentifikasjon.Identifikasjon.navnerom xml_char(200)

FME custom transformer NVDBAPI2GML

Parameters:
- apiString = @Value(_api)   # Tekst med kall til API
- xsd = C:\DATA\Standardisering\NVDBGML\XSD\Drenering.xsd   # xsd-fil
- xfmap_api = $(FME_MF_DIR)API_Mapping.xmp   # xfMap for API-mapping
- xfmap_xsd = $(FME_MF_DIR)NVDB_GML_SchemaMapper.xmp   # xfMap for XSD
- namespace = vegvesen.no.nvdb   # Attribute Value
- coordsys = EPSG:25833   # Koordinatsystem
- mfLocalPrefix =   # Prefiks for mappingfiler
- mfFT:   # Python Script
      mfLC = FME_MacroValues['mfLocalPrefix']+ '_ftMapping.csv'
      return mfLC

Input (input)
    -> HTTPFetcher_2
Note: Henter objekter fra NVDB-API
HTTPFetcher_2
    FOLLOW_REDIRECTS = Yes
    ERROR_ATTR = _error
    SAVE_FILE = No
    AUTH_METHOD = Basic
    REQUEST_HEADER:
      GET /vegobjekter HTTP/1.1
      Accept: application/vnd.vegvesen.nvdb-v1+xml
    TARGET_ATTR = _url_contents
    RESPONSE_HEADER_LIST_ATTR = _headers
    VERIFY_SSL_CERTIFICATES = Yes
    STATUS_CODE_ATTR = _http_status_code
    USE_COOKIES = No
    TARGET_URL = @Value(_api)
    PROXY_AUTH_METHOD = Basic
    -> XMLFeatureMapper
Note: Tolker XML
XMLFeatureMapper
    MERGE_ATTRS = Yes
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt
    XML_INPUT_TYPE = Attribute with XML document
    FEATURE_TYPE_ATTR = fme_feature_type
    SINGLE_XFMAP = $(xfmap_api)
    XML_SOURCE_NAME = _xml_source_
    ATTRIBUTE_XML = _url_contents
    CONFIGURATION_TYPE = Single xfMap file
    FEATURE_COUNT_PER_XML = _xml_feature_count_
    MAPPED -> GeometryReplacer
Note: Tildeler geometri
GeometryReplacer
    KIND_LONG = OGC Well Known Text
    SOURCE = @Value(geometriUtm33)
    REMOVE_ATTRIBUTE = Yes
    -> CoordinateSystemSetter
CoordinateSystemSetter
    COORDSYS = $(coordsys)
    -> SchemaMapper
    -> SchemaMapper_2
Note: Mapper egenskapsnavn til GML, vha applikasjonsskjemaet. Her er det noe som glipper for en del egenskaper!
SchemaMapper [off]
    IDXDESTATTR = fme_feature_type
    TABLE = element
    ROW_ID_ATTR = _schemamapper_row_ids
    XML_USE_HTTP_AUTH = NO
    IDXSOURCECOL = ""
    DATASET = $(xsd)
    MAP_ATTRS = NVDB_ID name """"""
    XML_CONTINUE_ON_GEOM_ERROR = yes
    XML_XFMAP = $(xfmap_xsd)
    IDXSOURCEATTR = fme_feature_type
    FORMAT = XML
    XML_FILE_TYPE = xfMap
    XML_CLIP_TO_ENVELOPE = NO
    IDXDESTCOL = ""
    MAPPED -> NullAttributeMapper_3
Note: Mapper egenskapsnavn til GML, vha koblingstabell
SchemaMapper_2
    IDXDESTCOL = ""
    CSV__SCHEMA = char,17,,number,3,0,number,6,0,char,22,
    CSV_SCAN_MAX_FEATURES = 1000
    IDXDESTATTR = fme_feature_type
    MATCH_ATTRS = ft_attr ftid
    CSV__STRIP_QUOTES = yes
    ROW_ID_ATTR = _schemamapper_row_ids
    TABLE = CSV
    IDXSOURCECOL = ""
    MAP_ATTRS = ptid name """"""
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SKIP_LINES = 1
    CSV__ALLOW_SPACES_IN_COLUMN_NAMES = yes
    CSV__DUPLICATE_DELIMS = no
    DATASET = C:\DATA\Standardisering\NVDBGML\XSD\Drenering_ptMapping.csv
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__SCHEMA_WITH_COL_NAMES = ft_attr,char,17,,ftid,number,3,0,ptid,number,6,0,name,char,22,
    IDXSOURCEATTR = fme_feature_type
    FORMAT = CSV
    CSV__SKIP_FOOTER = 0
    CSV__GROUP_BY_DATASET = no
    CSV__IN_FIELD_NAMES = YES
    CSV__FIELD_NAMES_AFTER_HEADER = no
    MAPPED -> NullAttributeMapper_3
NullAttributeMapper_3
    NULL_TREATMENT = Missing
    ATTRCHOICE = All Attributes
    SOURCE_ATTR_VAL = Empty Null
    -> SchemaMapper_3
Note: Mapperobjekttypenavn til GML, vha applikasjonsskjemaet
SchemaMapper_3
    IDXDESTCOL = name
    CSV__SCHEMA = number,3,0,char,18,
    CSV_SCAN_MAX_FEATURES = 1000
    IDXDESTATTR = fme_feature_type
    CSV__STRIP_QUOTES = yes
    ROW_ID_ATTR = _schemamapper_row_ids
    TABLE = CSV
    IDXSOURCECOL = NVDB_ID
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SKIP_LINES = 1
    CSV__ALLOW_SPACES_IN_COLUMN_NAMES = yes
    CSV__DUPLICATE_DELIMS = no
    DATASET = $(mfFT)
    CSV__IN_SEPARATOR = ;
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__SCHEMA_WITH_COL_NAMES = ftid,number,3,0,name,char,18,
    IDXSOURCEATTR = fme_feature_type
    FORMAT = CSV
    CSV__SKIP_FOOTER = 0
    CSV__GROUP_BY_DATASET = no
    CSV__IN_FIELD_NAMES = YES
    CSV__FIELD_NAMES_AFTER_HEADER = no
    MAPPED -> GeometryFilter
AttributeValueMapper_2
    VAL_ATTR = prosesshistorie
    DIRECTION = Forward (Source To Destination)
    DEFAULT_VALUE = Geometri: Generert fra lineære referanser til vegnett i NVDB
    LUT = true,Geometri: Egengeometri fra NVDB
    SRC = egengeometri
    -> AttributeExposer_2
AttributeExposer_2
    ATTR_LIST = NVDB_ID
    -> AttributeRenamer_3
Note: ID
AttributeRenamer_3
    ATTR_LIST = NVDB_ID,identifikasjon.Identifikasjon.lokalId,"","",identifikasjon.Identifikasjon.navnerom,$(namespace)
    -> AttributeKeeper
    -> AttributeRemover
AttributeRemover
    LIST_ATTRS = lineærPosisjon{}
    -> FeatureMerger [input 1]
AttributeKeeper
    KEEP_LIST = lineærPosisjon{}.felt lineærPosisjon{}.fraPosisjon lineærPosisjon{}.tilPosisjon lineærPosisjon{}.lineærtObjektIdentifikasjon.Identifikasjon.lokalId
    KEEP_ATTRS = identifikasjon.Identifikasjon.lokalId
    -> ListElementCounter
ListElementCounter
    LIST_NAME = lineærPosisjon{}
    CNT_ATTR = _element_count
    -> TestFilter
TestFilter
    DEFAULT_VALUE = Strekning
    TEST_LIST:
      BOOL_OP,AND,COMPOSITE_TEST,<Unused>,TEST_CLAUSE,"TEST @Value(lineærPosisjon{0}.fraPosisjon) = @Value(lineærPosisjon{0}.tilPosisjon)
      TEST @Value(_element_count) = 1",Punkt
    Punkt -> ListExploder
    Strekning -> ListExploder_2
FeatureMerger
    JOIN_KEYS = @Value(identifikasjon.Identifikasjon.lokalId) @Value(identifikasjon.Identifikasjon.lokalId) AUTO
    PROCESS_DUPS = No
    SUPPLIERS_FIRST = No
    ATTR_CONFLICT_RES = Use Requestor
    MERGE_TYPE = Attributes Only
    IGNORE_NULLS = No
    ATTR_ACCUM_MODE = Merge Supplier
    MERGED -> AttributeCreator_2
    NOT_MERGED -> AttributeCreator_2
AttributeCreator_2
    ATTR_LIST = gml_id,$(namespace).@Value(identifikasjon.Identifikasjon.lokalId)
    -> Output (output)
Output (output)

Bookmark: Definerer geometriegenskaper
GeometryFilter
    GEOM_PORT_NAMES = Point Line Area
    BREAK_AGG = No
    POINT -> GeometryPropertySetter
    LINE -> GeometryPropertySetter_2
    AREA -> GeometryPropertySetter_3
GeometryPropertySetter
    GEOM_NAME_FIELD = posisjon
    SETTYPE_PARAM = Geometry Name
    OVERWRITE_CHOICE = Yes
    SET -> AttributeValueMapper_2
GeometryPropertySetter_2
    GEOM_NAME_FIELD = senterlinje
    SETTYPE_PARAM = Geometry Name
    OVERWRITE_CHOICE = Yes
    SET -> AttributeValueMapper_2
GeometryPropertySetter_3
    GEOM_NAME_FIELD = område
    SETTYPE_PARAM = Geometry Name
    OVERWRITE_CHOICE = Yes
    SET -> AttributeValueMapper_2

Bookmark: Lager lineærPosisjon (punkt)
ListExploder
    INDEX_ATTR = _element_index
    INCOMING_PREFIX = lineærPosisjon.LineærPosisjonPunkt.
    LIST_ATTR = lineærPosisjon{}
    ATTR_ACCUM_MODE = Prefix Incoming List
    LIST_FOUND -> AttributeRenamer
AttributeRenamer
    ATTR_LIST = lineærPosisjon.LineærPosisjonPunkt.fraPosisjon,lineærPosisjon.LineærPosisjonPunkt.posisjon,,,lineærPosisjon.LineærPosisjonPunkt.lineærtObjektIdentifikasjon.Identifikasjon.navnerom,$(namespace).rl
    -> FeatureMerger [input 2]

Bookmark: Lager lineærPosisjon-liste (strekning)
ListExploder_2
    INDEX_ATTR = _element_index
    INCOMING_PREFIX = LineærPosisjonStrekning.
    LIST_ATTR = lineærPosisjon{}
    ATTR_ACCUM_MODE = Prefix Incoming List
    LIST_FOUND -> AttributeCreator
AttributeCreator
    ATTR_LIST = LineærPosisjonStrekning.lineærtObjektIdentifikasjon.Identifikasjon.navnerom,$(namespace).rl
    -> ListBuilder
ListBuilder
    LIST_NAME = lineærPosisjon
    GRP_BY = identifikasjon.Identifikasjon.lokalId
    -> FeatureMerger [input 2]
