FME workspace Vegnett_TNE2GML.fmw

Parameters:
- knr = 403   # Kommunenummer
- detaljNivå = Kjørefelt   # Detaljnivå
- Filename = Vegnettstest.gml
- DestDataset_GML = C:\DATA\Standardisering\NVDBGML\GML\Vegnettstest.gml   # Destination Geography Markup Language (GML) File
- namespace = vegvesen.no.nvdb   # " " Namespace

Writers:
- GML_1: GML to $(DestDataset_GML)

Note: Id-verdier
AttributeCreator_5
    ATTR_TABLE:
      SET_TO identifikasjon.Identifikasjon.lokalId = @Value(OID)
      SET_TO identifikasjon.Identifikasjon.navnerom = $(namespace)/rls
      SET_TO gml_id = $(namespace).rls.@Value(OID)
    -> FeatureMerger [input 1]
Note: Kobler CurveSegment til / RefLinkPart
InlineQuerier
    QUERY_SCHEMA = RefLinkPartExtended,REFLINK_OID,text,FROM_MEASURE,text,TO_MEASURE,text,RefLinkPart.fme_feature_content,fme_feature_content,CurveSegment.fme_feature_content,fme_feature_content
    TABLE_DEF = CurveSegment,REFLINK_OID,text,FROM_MEASURE,text,TO_MEASURE,text,RefLinkPart,REFLINK_OID,text,FROM_MEASURE,text,TO_MEASURE,text
    QUERY_DEF:
      RefLinkPartExtended,SELECT DISTINCT * FROM RefLinkPart
      INNER JOIN CurveSegment ON RefLinkPart.REFLINK_OID = CurveSegment.REFLINK_OID
      WHERE (RefLinkPart.FROM_MEASURE < CurveSegment.TO_MEASURE AND RefLinkPart.TO_MEASURE > CurveSegment.FROM_MEASURE) ,FIRST
    RefLinkPartExtended -> DuplicateRemover
    RefLinkPartExtended -> RefLinkPartExtended
Note: Fjerner duplikater
DuplicateRemover
    KEYATTR = OBJECTID
    UNIQUE -> GeometryPropertySetter_2
Note: Setter geometriegenskap
GeometryPropertySetter_2
    GEOM_NAME_FIELD = senterlinje
    OVERWRITE_CHOICE = Yes
    SETTYPE_PARAM = Geometry Name
    SET -> CoordinateRounder_2
CoordinateRounder_2
    YPREC = 3
    XPREC = 3
    ZPREC = 3
    ROUNDED -> AttributeCreator_2
Note: Id-verdier
AttributeCreator_2
    ATTR_TABLE:
      SET_TO identifikasjon.Identifikasjon.lokalId = @Value(OBJECTID)
      SET_TO identifikasjon.Identifikasjon.navnerom = $(namespace)/rlp
      SET_TO gml_id = $(namespace).rl.@Value(OBJECTID)
      SET_TO standardLRM = 2
    -> StringConcatenator_2
    -> StringConcatenator_3
Note: sekvens.xlink_href
StringConcatenator_3
    VAL_ATTR = sekvens.xlink_href
    ACTION = Create New Attribute
    PARM_LINE = $(Filename)#$(namespace).rls.@Value(REFLINK_OID)
    -> PythonCaller
Note: Mapping fra objekttype til typeVeg / NB / typeveg=Rundkjøring blir ikke brukt. / Krever kobling til Vegreferanse
AttributeValueMapper_4
    SRC = CLASS_CODE
    VAL_ATTR = typeveg
    DIRECTION = Forward (Source To Destination)
    LUT = 7001,Enkel bilveg,7012,Kanalisert veg,7011,Kanalisert veg,7201,Bilferje,7042,Gang- og sykkelveg,7046,Fortau,6304,Trapp
    DEFAULT_VALUE = Enkel bilveg
    -> NullAttributeMapper
NullAttributeMapper
    NULL_TREATMENT = Missing
    ATTRCHOICE = Selected Attributes
    ATTRLIST = kvalitet.Posisjonskvalitet.nøyaktighet kvalitet.Posisjonskvalitet.nøyaktighetHøyde detaljnivå kvalitet.Posisjonskvalitet.målemetode kvalitet.Posisjonskvalitet.målemetodeHøyde
    SOURCE_ATTR_VAL = Null Empty
    OTHER_VALUE = 0
    -> Veglenke (writer GML_1)
Veglenke (writer GML_1)
    attributes: nettverk.nilReason xml_buffer, nettverk.gml_remoteSchema xml_buffer, nettverk.xlink_href xml_buffer, nettverk.owns xml_boolean, standardLRM xml_buffer, måltLengde xml_real64, startposisjon xml_real64, sluttposisjon xml_real64, sekvens.nilReason xml_buffer, sekvens.gml_remoteSchema xml_buffer, sekvens.xlink_href xml_buffer, sekvens.owns xml_boolean, sluttnode.nilReason xml_buffer, sluttnode.gml_remoteSchema xml_buffer, sluttnode.xlink_href xml_buffer, sluttnode.owns xml_boolean, startnode.nilReason xml_buffer, startnode.gml_remoteSchema xml_buffer, startnode.xlink_href xml_buffer, startnode.owns xml_boolean, senterlinje xml_geometry, veglenkeadresse.Veglenkeadresse.kommunenummer xml_buffer, veglenkeadresse.Veglenkeadresse.adressekode xml_int64, veglenkeadresse.Veglenkeadresse.adressenavn xml_buffer, veglenkeadresse.Veglenkeadresse.sideveg xml_boolean, brøytes xml_boolean, detaljnivå xml_buffer, feltoversikt xml_buffer, trafikkreguleringer xml_buffer, konnekteringslenke xml_boolean,
      typeVeg xml_buffer, veglenkeFraDato xml_date, veglenkeTilDato xml_date, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer
RefLinkPartExtended: Inspector
    TACKATTRS = CLASS_CODE
Veglenkesett (writer GML_1)
    attributes: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

Bookmark: Kommune
Creator_2
    NUM = 1
    GEOMTYPE = Geometry Object
    CREATED -> AttributeCreator_3
Note: Nettverk-id
AttributeCreator_3
    ATTR_TABLE = SET_TO _nettverk_id = $(namespace).nv.$(knr)
    -> AttributeRenamer
    -> StringConcatenator_6
StringConcatenator_6
    VAL_ATTR = _kommunewhere
    ACTION = Create New Attribute
    PARM_LINE = KOMM=$(knr)
    -> StringConcatenator
StringConcatenator
    VAL_ATTR = nettverk.xlink_href
    ACTION = Create New Attribute
    PARM_LINE = $(Filename)#@Value(_nettverk_id)
    -> FeatureReader
FeatureReader
    WHERE = @Value(_kommunewhere)
    FORMAT = GEODATABASE_FILE
    ATTR_ACCUM_MODE = Merge Initiator and Result
    ATTR_CONFLICT_RES = Use Result
    INTERACT = <No Spatial Filter>
    COMBINE_GEOM = Use Result
    ATTRIBUTES = N250_AdminFlate,"OBJECTID,OBJTYPE,NAVN,KOMM,OPPDATERINGSDATO,Shape_Length,Shape_Area",N250_AdminGrense,"OBJECTID,OBJTYPE,OPPDATERINGSDATO,Shape_Length",N250_AdminGrensePunkt,"OBJECTID,OBJTYPE,GRENSEPUNKTTYPE,GRENSEPUNKTNUMMER,GRUNNLINJENUMMER,NAVN,OPPDATERINGSDATO",N250_AnleggsLinje,"OBJECTID,OBJTYPE,OPPDATERINGSDATO,Shape_Length",N250_AnleggsPunkt,"OBJECTID,OBJTYPE,FYRLISTENUMMER,OPPDATERINGSDATO",N250_ArealdekkeFlate,"OBJECTID,OBJTYPE,VANNBR,HOYDE,VATNLNR,OPPDATERINGSDATO,Shape_Length,Shape_Area",N250_ArealdekkePunkt,"OBJECTID,OBJTYPE,NAVN,OPPDATERINGSDATO",N250_Bane,"OBJECTID,OBJTYPE,JERNBANETYPE,SPORANTALL,MEDIUM,OPPDATERINGSDATO,Shape_Length",N250_BegrensningsKurve,"OBJECTID,OBJTYPE,OPPDATERINGSDATO,Shape_Length",N250_BygningsPunkt,"OBJECTID,OBJTYPE,BYGGKAT,OPPDATERINGSDATO",N250_ElvBekk,"OBJECTID,OBJTYPE,VANNBR,OPPDATERINGSDATO,Shape_Length",N250_Ferge,"OBJECTID,OBJTYPE,VEGKATEGORI,VEGNUMMER,OPPDATERINGSDATO,Shape_Length",N250_Grunnlinje,"OBJECTID,OBJTYPE,OPPDATERINGSDATO,Shape_Length",N250_HoydeKontur,"OBJECTID,OBJTYPE,HOYDE,OPPDATERINGSDATO,MEDIUM,Shape_Length",N250_HoydeLag,"OBJECTID,OBJTYPE,MINHOYDE,MAKSHOYDE,OPPDATERINGSDATO,Shape_Length,Shape_Area",N250_HoydePunkt,"OBJECTID,OBJTYPE,HOYDE,OPPDATERINGSDATO",N250_Hoydetall,"OBJECTID,FeatureID,ZOrder,AnnotationClassID,SymbolID,Status,TextString,FontName,FontSize,Bold,Italic,Underline,VerticalAlignment,HorizontalAlignment,XOffset,YOffset,Angle,FontLeading,WordSpacing,CharacterWidth,CharacterSpacing,FlipAngle,Override,TEKSTT_,TEKS_ID,OBJTYPE,NAVNTYPE,SKRIFTKODE,SPERRING,TRNORD,TROST,SNAVN,SSR_ID,STRENG,ID,SYMBOL,LEVEL_,FRISPERR,OPPDATERINGSDATO,Shape_Length,Shape_Area,OBJEKT_X,OBJEKT_Y",N250_JernbaneStasjon,"OBJECTID,OBJTYPE,NAVN,STASJONSFORMAL,OPPDATERINGSDATO",N250_LufthavnPunkt,"OBJECTID,OBJTYPE,ICAO_KODE,IATA_KODE,LUFTHAVNTYPE,TRAFIKKTYPE,NAVN,EIER,OPPDATERINGSDATO",N250_Navn,"OBJECTID,FeatureID,ZOrder,AnnotationClassID,SymbolID,Status,TextString,FontName,FontSize,Bold,Italic,Underline,VerticalAlignment,HorizontalAlignment,XOffset,YOffset,Angle,FontLeading,WordSpacing,CharacterWidth,CharacterSpacing,FlipAngle,Override,TEKST_,TEKST_ID,OBJTYPE,NAVNTYPE,SKRIFTKODE,SPERRING,TRNORD,TROST,SNAVN,SSR_ID,STRENG,ID,SYMBOL,LEVEL_,FRISPERR,OPPDATERINGSDATO,Shape_Length,Shape_Area,OBJEKT_X,OBJEKT_Y",N250_TettSted,"OBJECTID,OBJTYPE,TSTED,OPPDATERINGSDATO",N250_TuristHytte,"OBJECTID,OBJTYPE,NAVN,BETJENINGSGRAD,HYTTEEIER,OPPDATERINGSDATO,BYGGKAT",N250_VegSti,"OBJECTID,OBJTYPE,VEGKATEGORI,VEGNUMMER,VEGSTATUS,MOTORVEGTYPE,MEDIUM,RUTEMERKING,OPPDATERINGSDATO,Shape_Length",N250_VerneOmrade,"OBJECTID,OBJTYPE,NAVN,VERNEFORM,OPPDATERINGSDATO,VERNEDATO,Shape_Length,Shape_Area"
    SUPPORTED_SPATIAL_INTERACTIONS = ENVELOPE_INTERSECT%INTERSECTS%CONTAINS%CROSSES%DISJOINT%EQUALS%OVERLAPS%TOUCHES%WITHIN
    FEATURETYPES_RADIO = FEATURETYPES
    DATASET = K:\Vektor\00\23-N250\00\EsriGDB\N250.gdb
    OUTPUT_FEATURES_DISPLAY = Based on Connections
    FEATURETYPES = N250_AdminFlate
    N250_AdminFlate -> Dissolver
Dissolver
    CONNECT_Z_MODE = First Wins
    ACCUM_INPUT_ATTRS = No
    GROUP_BY = KOMM nettverk.xlink_href
    NO_OVRLP = No
    AREA -> DonutHoleExtractor
DonutHoleExtractor
    OUTERSHELL -> FeatureReader_2
    OUTERSHELL -> FeatureReader_3
Note: Reflink
FeatureReader_3
    GEODATABASE_SDE_CHECK_SIMPLE_GEOM = no
    FORMAT = GEODATABASE_SDE
    GEODATABASE_SDE_REMOVE_TABLE_QUALIFIER = NO
    GEODATABASE_SDE_SPLIT_COMPLEX_EDGES = no
    GEODATABASE_SDE_CACHE_MULTIPATCH_TEXTURES = no
    GEODATABASE_SDE_RESOLVE_DOMAINS = no
    ATTR_ACCUM_MODE = Merge Initiator and Result
    GEODATABASE_SDE_IGNORE_RELATIONSHIP_INFO = no
    GEODATABASE_SDE_USE_SEARCH_ENVELOPE = NO
    ATTR_CONFLICT_RES = Use Result
    GEODATABASE_SDE_MERGE_FEAT_LINKED_ANNOS = no
    GEODATABASE_SDE_CLIP_TO_ENVELOPE = NO
    GEODATABASE_SDE_SPLIT_MULTI_PART_ANNOS = no
    GEODATABASE_SDE_IGNORE_NETWORK_INFO = no
    GEODATABASE_SDE_RESOLVE_SUBTYPE_NAMES = no
    INTERACT = Intersects
    COMBINE_GEOM = Use Result
    GEODATABASE_SDE_CREDENTIALS_OVERRIDE = NO
    GEODATABASE_SDE_FEATURE_READ_MODE = Features
    GEODATABASE_SDE_SPLIT_COMPLEX_ANNOS = no
    ATTRIBUTES = SDE_TNE.TNE_RefLink,"OBJECTID,OID,VID,REFOBJ_TYPE,NEXT_FREE_PORT_NUMBER,LENGTH,FIXED_LENGTH,SHAPE.LEN"
    GEODATABASE_SDE_VERSION_OVERRIDE = NO
    SUPPORTED_SPATIAL_INTERACTIONS = ENVELOPE_INTERSECT%INTERSECTS%CONTAINS%CROSSES%DISJOINT%EQUALS%OVERLAPS%TOUCHES%WITHIN
    FEATURETYPES_RADIO = FEATURETYPES
    GEODATABASE_SDE_ALIAS_MODE = NONE
    OUTPUT_FEATURES_DISPLAY = Based on Connections
    GEODATABASE_SDE_PERSISTENT_CONNECTION = no
    GEODATABASE_SDE_TRANSLATE_SPATIAL_DATA_ONLY = no
    FEATURETYPES = SDE_TNE.TNE_RefLink
    GEODATABASE_SDE_CONNECTION_FILE = C:\Users\knjetl\AppData\Roaming\ESRI\Desktop10.2\ArcCatalog\PTNE-sde_tne_read@svvkartp.vegvesen.no.sde
    SDE_TNE.TNE_RefLink -> AttributeCreator_5
Note: CurveSegment, RefLinkPart og RefNode
FeatureReader_2
    GEODATABASE_SDE_CHECK_SIMPLE_GEOM = no
    WHERE = TO_DATE = 99991231
    FORMAT = GEODATABASE_SDE
    GEODATABASE_SDE_REMOVE_TABLE_QUALIFIER = NO
    GEODATABASE_SDE_SPLIT_COMPLEX_EDGES = no
    GEODATABASE_SDE_CACHE_MULTIPATCH_TEXTURES = no
    GEODATABASE_SDE_RESOLVE_DOMAINS = no
    ATTR_ACCUM_MODE = Merge Initiator and Result
    GEODATABASE_SDE_IGNORE_RELATIONSHIP_INFO = no
    GEODATABASE_SDE_USE_SEARCH_ENVELOPE = NO
    ATTR_CONFLICT_RES = Use Result
    GEODATABASE_SDE_MERGE_FEAT_LINKED_ANNOS = no
    GEODATABASE_SDE_CLIP_TO_ENVELOPE = NO
    GEODATABASE_SDE_SPLIT_MULTI_PART_ANNOS = no
    GEODATABASE_SDE_IGNORE_NETWORK_INFO = no
    GEODATABASE_SDE_RESOLVE_SUBTYPE_NAMES = no
    INTERACT = Intersects
    COMBINE_GEOM = Use Result
    GEODATABASE_SDE_CREDENTIALS_OVERRIDE = NO
    GEODATABASE_SDE_FEATURE_READ_MODE = Features
    GEODATABASE_SDE_SPLIT_COMPLEX_ANNOS = no
    ATTRIBUTES = SDE_TNE.TNE_CurveSegment,"OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,MUNICIPALITY,SHAPE.LEN",SDE_TNE.TNE_RefLinkPart,"OBJECTID,REFLINK_OID,FROM_DATE,TO_DATE,FROM_MEASURE,TO_MEASURE,FROM_REFNODE_OID,TO_REFNODE_OID,LENGTH,TOPOLOGY_LEVEL,SUPER_OID,SUPER_FROM_MEASURE,SUPER_TO_MEASURE,LANE,DIRECTION,SHAPE.LEN",SDE_TNE.TNE_RefNode,"OBJECTID,OID,VID,REFOBJ_TYPE,NEXT_FREE_PORT_NUMBER,FROM_DATE,TO_DATE"
    GEODATABASE_SDE_VERSION_OVERRIDE = NO
    SUPPORTED_SPATIAL_INTERACTIONS = ENVELOPE_INTERSECT%INTERSECTS%CONTAINS%CROSSES%DISJOINT%EQUALS%OVERLAPS%TOUCHES%WITHIN
    FEATURETYPES_RADIO = FEATURETYPES
    GEODATABASE_SDE_ALIAS_MODE = NONE
    OUTPUT_FEATURES_DISPLAY = Based on Connections
    GEODATABASE_SDE_PERSISTENT_CONNECTION = no
    GEODATABASE_SDE_TRANSLATE_SPATIAL_DATA_ONLY = no
    FEATURETYPES = SDE_TNE.TNE_CurveSegment SDE_TNE.TNE_RefLinkPart SDE_TNE.TNE_RefNode
    GEODATABASE_SDE_CONNECTION_FILE = C:\Users\knjetl\AppData\Roaming\ESRI\Desktop10.2\ArcCatalog\PTNE-sde_tne_read@svvkartp.vegvesen.no.sde
    SDE_TNE.TNE_RefLinkPart -> PythonCaller_3
    SDE_TNE.TNE_RefNode -> CoordinateRounder
    SDE_TNE.TNE_CurveSegment -> InlineQuerier [input 1]

Bookmark: Nettverk
AttributeRenamer
    ATTR_TABLE = RENAME_SET_DEFAULT _nettverk_id > gml_id
    -> Nettverk (writer GML_1)
Nettverk (writer GML_1)
    attributes: nettverkselement{}.nilReason xml_buffer, nettverkselement{}.gml_remoteSchema xml_buffer, nettverkselement{}.xlink_href xml_buffer, nettverkselement{}.owns xml_boolean

Bookmark: Detaljnivå
Note: Finner valgt detaljnivå
PythonCaller_3
    NEW_ATTRIBUTES = _topoWhere
    PYTHONSYMBOL = topolevel
    PYTHONSOURCE:
      import fmeobjects

      def topolevel(feature):
          par = '0,1,2,3'
          if FME_MacroValues['detaljNivå'] == 'Vegtrase':
              par = '0,1'
          elif FME_MacroValues['detaljNivå'] == 'Kjørebane':
              par = '1,2'
          elif FME_MacroValues['detaljNivå'] == 'Kjørefelt':
              par = '1,2,3'
          feature.setAttribute("_topoWhere", par)
    -> TestFilter_4
Note: Finner lenker som skal være med
TestFilter_4
    TEST_LIST = BOOL_OP,OR,COMPOSITE_TEST,<Unused>,TEST_CLAUSE,"TEST @Value(TOPOLOGY_LEVEL) IN @Value(_topoWhere)",TOPOLEVEL
    DEFAULT_VALUE = <UNFILTERED>
    TOPOLEVEL -> InlineQuerier [input 2]

Bookmark: Veglenkesekvens
StringConcatenator_2
    VAL_ATTR = xlink_href
    ACTION = Create New Attribute
    PARM_LINE = $(Filename)#@Value(gml_id)
    -> AttributeKeeper
AttributeKeeper
    KEEP_ATTRS = REFLINK_OID,xlink_href
    -> FeatureMerger [input 2]
FeatureMerger
    ATTR_ACCUM_MODE = Merge Supplier
    JOIN_KEYS = @Value(OID) @Value(REFLINK_OID) AUTO
    GEOM_TYPE = Build Polygons
    ATTR_CONFLICT_RES = Use Requestor
    LIST_NAME = sekvensdel
    PROCESS_DUPS = Yes
    IGNORE_NULLS = No
    SUPPLIERS_FIRST = No
    CONNECT_Z_MODE = First Wins
    MERGE_TYPE = Attributes Only
    MERGED -> Veglenkesekvens (writer GML_1)
Veglenkesekvens (writer GML_1)
    attributes: nettverk.nilReason xml_buffer, nettverk.gml_remoteSchema xml_buffer, nettverk.xlink_href xml_buffer, nettverk.owns xml_boolean, standardLRM xml_buffer, måltLengde xml_real64, sekvensdel{}.nilReason xml_buffer, sekvensdel{}.gml_remoteSchema xml_buffer, sekvensdel{}.xlink_href xml_buffer, sekvensdel{}.owns xml_boolean, identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer

Bookmark: Døper om og mapper egenskaper
Note: Ordner nullverdier for kvalitetsattributter
PythonCaller
    PYTHONSYMBOL = processFeature
    PYTHONSOURCE:
      import fmeobjects
      # Template Function interface:
      def processFeature(feature):
          par=feature.getAttribute('QUALITY_METHOD')
          if par == -1 or par == 0:
              feature.removeAttribute('QUALITY_METHOD')
          par=feature.getAttribute('QUALITY_ACCURACY')
          if par == -1 or par == 0:
              feature.removeAttribute('QUALITY_ACCURACY')
          par=feature.getAttribute('QUALITY_METHOD_HEIGHT')
          if par == -1 or par == 0:
              feature.removeAttribute('QUALITY_METHOD_HEIGHT')
          par=feature.getAttribute('QUALITY_ACCURACY_HEIGHT')
          if par == -1 or par == 0:
              feature.removeAttribute('QUALITY_ACCURACY_HEIGHT')
    -> AttributeRenamer_2
AttributeRenamer_2
    ATTR_LIST = QUALITY_METHOD,kvalitet.Posisjonskvalitet.målemetode,"",QUALITY_ACCURACY,kvalitet.Posisjonskvalitet.nøyaktighet,"",QUALITY_METHOD_HEIGHT,kvalitet.Posisjonskvalitet.målemetodeHøyde,"",QUALITY_ACCURACY_HEIGHT,kvalitet.Posisjonskvalitet.nøyaktighetHøyde,"",KOMM,kommune,"",FROM_DATE,veglenkeFraDato,"",TO_DATE,veglenkeTilDato,""
    -> AttributeValueMapper_3
Note: medium
AttributeValueMapper_3
    SRC = MEDIUM
    VAL_ATTR = medium
    DIRECTION = Forward (Source To Destination)
    LUT = 0,T,1,B,2,L,3,U
    DEFAULT_VALUE = T
    -> AttributeCopier
Note: lenkeposisjoner
AttributeCopier
    ATTR_LIST = FROM_MEASURE,startposisjon,"",TO_MEASURE,sluttposisjon,""
    -> AttributeValueMapper
    -> AttributeValueMapper_2
Note: konnekteringslenke / NB! Må løeses på andre måter nå, ligger i vegnettsmodellen
AttributeValueMapper [off]
    SRC = CLASS_CODE
    VAL_ATTR = konnekteringslenke
    DIRECTION = Forward (Source To Destination)
    LUT = 7004,true
    DEFAULT_VALUE = false
    -> AttributeValueMapper_2
Note: detaljnivå
AttributeValueMapper_2
    SRC = TOPOLOGY_LEVEL
    VAL_ATTR = detaljnivå
    DIRECTION = Forward (Source To Destination)
    LUT = 0,Vegtrase,2,Kjørebane,3,Kjørefelt
    DEFAULT_VALUE = FME_NULL_VALUE
    -> DateFormatter
DateFormatter
    DATE_ATTR = veglenkeFraDato,veglenkeTilDato
    SRCFMT = Unknown - Automatic Detection
    FMT = ISO Date (%Y-%m-%d)
    INVALID_DATE_VALUE = _FME_NO_OP_
    -> TestFilter_2

Bookmark: Overodnet lenke for objekttypene Svingekonnekteringslenke og Kjørefelt
Note: Skiller ut / Svingekonnekteringslenker / og Kjørefeltlenker
TestFilter_2
    TEST_LIST = BOOL_OP,OR,COMPOSITE_TEST,<Unused>,TEST_CLAUSE,"TEST @Value(CLASS_CODE) = 7004",Svingekonnekteringslenke,BOOL_OP,OR,COMPOSITE_TEST,<Unused>,TEST_CLAUSE,"TEST @Value(CLASS_CODE) = 7010",Kjørefelt
    DEFAULT_VALUE = <UNFILTERED>
    Svingekonnekteringslenke -> BulkAttributeRenamer_2
    Kjørefelt -> BulkAttributeRenamer_2
    <UNFILTERED> -> InlineQuerier_2 [input 2]
    <UNFILTERED> -> AttributeValueMapper_4
BulkAttributeRenamer_2
    ATTRCHOICE = Selected Attributes
    ATTRLIST = CLASS_CODE
    PATTERN_ACTION_DISP = Add String Prefix
    REPLACE_STR = FLD
    -> InlineQuerier_2 [input 1]
Note: Koblertil overodnet lenke
InlineQuerier_2
    QUERY_SCHEMA = Ut,SUPER_OID,text,SUPER_FROM_MEASURE,text,SUPER_TO_MEASURE,text,OBJECTID,text,Kjørefelt.fme_feature_content,fme_feature_content,CLASS_CODE,text
    TABLE_DEF = Kjørefelt,SUPER_OID,text,SUPER_FROM_MEASURE,text,SUPER_TO_MEASURE,text,OBJECTID,text,Andre,REFLINK_OID,text,FROM_MEASURE,text,TO_MEASURE,text,CLASS_CODE,text
    QUERY_DEF:
      Ut,SELECT DISTINCT Kjørefelt.*, Andre.CLASS_CODE FROM Kjørefelt
      INNER JOIN Andre ON Kjørefelt.SUPER_OID = Andre.REFLINK_OID
      WHERE (Kjørefelt.SUPER_FROM_MEASURE < Andre.TO_MEASURE AND Kjørefelt.SUPER_TO_MEASURE > Andre.FROM_MEASURE) ,FIRST
    Ut -> DuplicateRemover_2
Note: Fjerner duplikater
DuplicateRemover_2
    KEYATTR = OBJECTID
    UNIQUE -> AttributeValueMapper_4

Bookmark: Vegnode
CoordinateRounder
    YPREC = 3
    XPREC = 3
    ZPREC = 3
    ROUNDED -> GeometryPropertySetter
Note: Setter geometriegenskap
GeometryPropertySetter
    GEOM_NAME_FIELD = posisjon
    OVERWRITE_CHOICE = Yes
    SETTYPE_PARAM = Geometry Name
    SET -> AttributeCreator
Note: Id-verdier
AttributeCreator
    ATTR_TABLE:
      SET_TO identifikasjon.Identifikasjon.lokalId = @Value(OBJECTID)
      SET_TO identifikasjon.Identifikasjon.navnerom = $(namespace)/rn
      SET_TO gml_id = $(namespace).rn.@Value(OID)
    -> Vegnode (writer GML_1)
Vegnode (writer GML_1)
    attributes: sluttnodeFor{}.nilReason xml_buffer, sluttnodeFor{}.gml_remoteSchema xml_buffer, sluttnodeFor{}.xlink_href xml_buffer, sluttnodeFor{}.owns xml_boolean, startnodeFor{}.nilReason xml_buffer, startnodeFor{}.gml_remoteSchema xml_buffer, startnodeFor{}.xlink_href xml_buffer, startnodeFor{}.owns xml_boolean, posisjon xml_geometry, identifikasjon.Identifikasjon.lokalId xml_buffer, identifikasjon.Identifikasjon.navnerom xml_buffer, identifikasjon.Identifikasjon.versjonId xml_buffer, nettverk.nilReason xml_buffer, nettverk.gml_remoteSchema xml_buffer, nettverk.xlink_href xml_buffer, nettverk.owns xml_boolean, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer
