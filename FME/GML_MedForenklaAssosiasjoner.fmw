FME workspace GML_MedForenklaAssosiasjoner.fmw

Parameters:
- SourceDataset_GML = C:\DATA\GitHub\NVDBGML\GML\Test\520\*.gml   # Source Geography Markup Language (GML) File(s)
- ftIDxtra = 297;446;277;762;761   # " " Ekstra objekttyper
- Kommune = 520   # Kommunenummer
- gmlFolder = C:\DATA\GitHub\NVDBGML\GML\Test   # GML-hovedmappe
- gmlNs = https://raw.githubusercontent.com/jetgeo/NVDBGML/master/XSD/NIFS   # GML Namespace
- xsdName = Stikkrenne   # Applikasjonsskjemanavn
- xsd:   # Python Script
      xsd = FME_MacroValues['gmlNs'] + '/' + FME_MacroValues['xsdName'] + '.xsd'
      return xsd
- sl:   # Python Script
      sl = FME_MacroValues['gmlNs'] + ' ' + FME_MacroValues['gmlNs'] + '/' + FME_MacroValues['xsdName'] + '.xsd'
      return sl

Readers:
- GML_1: GML from $(SourceDataset_GML)

Writers:
- GML_2: GML to $(gmlFolder)\n$(Kommune)

Generell (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, vegreferanse{}.Vegreferanse.veglenkeMeterFra xml_int64, vegreferanse{}.Vegreferanse.veglenkeMeterTil xml_int64, vegreferanse{}.Vegreferanse.referanseretning xml_buffer, vegreferanse{}.Vegreferanse.vegreferanseFraDato xml_date, vegreferanse{}.Vegreferanse.vegreferanseTilDato xml_date, bruksområde xml_buffer, type xml_buffer, navnPåStrekning xml_buffer, byggeår xml_int64,
      tenningssystem xml_buffer, dimming xml_buffer, fjernstyring xml_buffer, avstandInnbyrdes xml_int64, luminansnivå xml_buffer, eier xml_buffer, eierNavn xml_buffer, vedlikeholdsansvarlig xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.fraPosisjon xml_real64, lineærPosisjon{}.LineærPosisjonStrekning.tilPosisjon xml_real64, assosiertKommentar{}.owns xml_boolean, assosiertKommentar{}.nilReason xml_buffer, assosiertKommentar{}.gml_remoteSchema xml_buffer, assosiertKommentar{}.xlink_href xml_buffer, assosiertDokumentasjon{}.owns xml_boolean, assosiertDokumentasjon{}.nilReason xml_buffer, assosiertDokumentasjon{}.gml_remoteSchema xml_buffer, assosiertDokumentasjon{}.xlink_href xml_buffer, assosiertBelysningspunkt{}.owns xml_boolean, assosiertBelysningspunkt{}.nilReason xml_buffer, assosiertBelysningspunkt{}.gml_remoteSchema xml_buffer, assosiertBelysningspunkt{}.xlink_href xml_buffer
    -> AttributeExposer
AttributeExposer
    ATTR_LIST = fme_feature_type
    -> Joiner
Joiner
    MATCH_RULE_DISPLAY = Match All (1:M)
    CSV__IN_SEPARATOR = ;
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_FIELD_NAMES = YES
    FORMAT = CSV
    ATTR_CONFLICT_RES = Use Original
    DATASET = https://raw.githubusercontent.com/jetgeo/NVDBGML/master/XSD/NVDB_ftMapping.csv
    CSV__ALLOW_SPACES_IN_COLUMN_NAMES = yes
    CSV_SCAN_MAX_FEATURES = 1000
    CSV__FIELD_NAMES_AFTER_HEADER = no
    CSV__DUPLICATE_DELIMS = no
    MATCH_MULTIPLE_DISPLAY = Create a feature for each match
    CSV__GROUP_BY_DATASET = no
    ATTR_ACCUM_MODE = Merge Joined
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SKIP_FOOTER = 0
    JOIN_KEYS = fme_feature_type name
    CSV__SKIP_LINES = 1
    CSV__STRIP_QUOTES = yes
    CSV__SCHEMA_WITH_COL_NAMES = ftid,number,4,0,name,char,23,
    ADDED_FIELDS = ftid
    TABLE = CSV
    CSV__SCHEMA = number,4,0,char,23,
    JOINED -> FeatureMerger [REQUESTOR]
FeatureMerger
    JOIN_KEYS = @Value(ftid) @Value(ftid) AUTO
    ATTR_CONFLICT_RES = Use Requestor
    ATTR_ACCUM_MODE = Merge Supplier
    MERGE_TYPE = Attributes Only
    REJECT_NULL_MISSING_KEYS = No
    IGNORE_NULLS = No
    SUPPLIERS_FIRST = No
    PROCESS_DUPS = No
    MERGED -> StringConcatenator
    NOT_MERGED -> PythonCaller_2
Note: Lager full xlink_href for objektet
StringConcatenator
    PARM_LINE = @Value(fme_feature_type).gml#@Value(gml_id)
    VAL_ATTR = xlink_href
    ACTION = Create New Attribute
    -> ListBasedFeatureMerger [Supplier]
Note: Lager én liste av alle assosiert*{}.xlink_href
PythonCaller_2
    PYTHONSYMBOL = getAssNVDB_ID
    NEW_ATTRIBUTES = aList{}.xlink_href
    PYTHONSOURCE:
      import fme
      import fmeobjects
      # Template Function interface:
      # When using this function, make sure its name is set as the value of
      # the 'Class or Function to Process Features' transformer parameter
      def getAssNVDB_ID(feature):
          anames= feature.getAllAttributeNames()
          i=0
          for aname in anames:
              if aname.startswith('assosiert') and aname.endswith('xlink_href'):
                  v = feature.getAttribute(aname)
                  pos=v.rfind('.')
                  if pos != -1:
                      nvdb_id=v[pos+1:]
                  else:
                      nvdb_id=v
                  feature.setAttribute('aList{%d}.xlink_href' % i, v)
                  i+=1
    -> ListBasedFeatureMerger [Requestor]
ListBasedFeatureMerger
    MODE = AUTO
    LIST_NAME = _assosiasjonsliste
    REFERATTR = aList{}.xlink_href
    ATTR_ACCUM_MODE = Prefix Supplier
    MERGE_TYPE = Attributes Only
    REFEEATTR = @Value(xlink_href)
    IGNORE_NULLS = No
    BUILD_INCOMPLETE = Merge Supplier Information
    SUPPLIER_PREFIX = assosiertObjekt.
    PROCESS_DUPS = Yes
    Merged -> PythonCaller_3
    NotMerged -> ListBasedFeatureMerger_NotMerged_-__Vegobjekttype
Note: Lager én liste pr assosiert objekttype
PythonCaller_3
    PYTHONSYMBOL = assToAttr
    PYTHONSOURCE:
      import fme
      import fmeobjects

      def assToAttr(feature):

          ft=FME_MacroValues['ftIDxtra']
          ftl=ft.split(';')

          # unik liste med attributtnavn for listeobjektene
          lanames = set()
          anames= feature.getAllAttributeNames()
          for aname in anames:
              if aname.startswith('_assosiasjonsliste{'):
                  pos=aname.rfind('}')
                  if pos != -1:
                      saname=aname[pos+2:]
                      lanames.add(saname)


          for ft in ftl:
              #Løkke for hver objekttype som skal bli attributter
              i=0
              j=0
              while True:
                  ftid=str(feature.getAttribute('_assosiasjonsliste{%d}.ftid' % i))
                  if ftid == 'None':
                      break

                  if ftid==ft:
                      ftn=str(feature.getAttribute('_assosiasjonsliste{%d}.fme_feature_type' % i))
                      attrn=ftn[0].lower() + ftn[1:]
                      for aname in lanames:
                          olstn = '_assosiasjonsliste{%d}.' + aname
                          nlstn = attrn + '{%d}.' + ftn  + '.' + aname
                          v=feature.getAttribute(olstn % i)
                          if v != None:
                              feature.setAttribute(nlstn % j,v)
                      j+=1
                  i+=1
    -> ListBasedFeatureMerger_NotMerged_-__Vegobjekttype
    -> _p
_p: Inspector
    TACKATTRS = fme_feature_type
ListBasedFeatureMerger_NotMerged_-__Vegobjekttype: Junction
    -> Vegobjekttype (writer GML_2)
    -> _
_: Inspector [off]
    TACKATTRS = fme_feature_type
Vegobjekttype (writer GML_2)
    attributes: identifikasjon.Identifikasjon.lokalId xml_char(200), identifikasjon.Identifikasjon.navnerom xml_char(200), identifikasjon.Identifikasjon.versjonId xml_char(200), endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, vegreferanse{}.Vegreferanse.veglenkeMeterFra xml_int64, vegreferanse{}.Vegreferanse.veglenkeMeterTil xml_int64, vegreferanse{}.Vegreferanse.referanseretning xml_buffer, vegreferanse{}.Vegreferanse.vegreferanseFraDato xml_date, vegreferanse{}.Vegreferanse.vegreferanseTilDato xml_date, bruksområde xml_buffer, type xml_buffer, navnPåStrekning xml_buffer, byggeår xml_int64,
      tenningssystem xml_buffer, dimming xml_buffer, fjernstyring xml_buffer, avstandInnbyrdes xml_int64, luminansnivå xml_buffer, eier xml_buffer, eierNavn xml_buffer, vedlikeholdsansvarlig xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.fraPosisjon xml_real64, lineærPosisjon{}.LineærPosisjonStrekning.tilPosisjon xml_real64, assosiertKommentar{}.owns xml_boolean, assosiertKommentar{}.nilReason xml_buffer, assosiertKommentar{}.gml_remoteSchema xml_buffer, assosiertKommentar{}.xlink_href xml_buffer, assosiertDokumentasjon{}.owns xml_boolean, assosiertDokumentasjon{}.nilReason xml_buffer, assosiertDokumentasjon{}.gml_remoteSchema xml_buffer, assosiertDokumentasjon{}.xlink_href xml_buffer, assosiertBelysningspunkt{}.owns xml_boolean, assosiertBelysningspunkt{}.nilReason xml_buffer, assosiertBelysningspunkt{}.gml_remoteSchema xml_buffer, assosiertBelysningspunkt{}.xlink_href xml_buffer, gml_parent_id xml_buffer, gml_parent_property xml_buffer, ftid xml_char(200), _matched_records xml_char(200),
      aList{}.xlink_href xml_char(200), assosiertObjekt.identifikasjon.Identifikasjon.lokalId xml_char(200), assosiertObjekt.identifikasjon.Identifikasjon.navnerom xml_char(200), assosiertObjekt.identifikasjon.Identifikasjon.versjonId xml_char(200), assosiertObjekt.endringsflagg.Endringsflagg.typeEndring xml_char(200), assosiertObjekt.endringsflagg.Endringsflagg.tidspunktEndring xml_char(200), assosiertObjekt.datafangstdato xml_char(200), assosiertObjekt.oppdateringsdato xml_char(200), assosiertObjekt.kvalitet.Posisjonskvalitet.målemetode xml_char(200), assosiertObjekt.kvalitet.Posisjonskvalitet.nøyaktighet xml_char(200), assosiertObjekt.kvalitet.Posisjonskvalitet.synbarhet xml_char(200), assosiertObjekt.kvalitet.Posisjonskvalitet.målemetodeHøyde xml_char(200), assosiertObjekt.kvalitet.Posisjonskvalitet.nøyaktighetHøyde xml_char(200), assosiertObjekt.kvalitet.Posisjonskvalitet.maksimaltAvvik xml_char(200), assosiertObjekt.prosesshistorie xml_char(200), assosiertObjekt.høydereferanse xml_char(200), assosiertObjekt.kommunenummer xml_char(200), assosiertObjekt.sideposisjon xml_char(200), assosiertObjekt.vegreferanse{}.Vegreferanse.vegkategori xml_char(200), assosiertObjekt.vegreferanse{}.Vegreferanse.vegstatus xml_char(200), assosiertObjekt.vegreferanse{}.Vegreferanse.vegnummer xml_char(200), assosiertObjekt.vegreferanse{}.Vegreferanse.hovedParsell xml_char(200), assosiertObjekt.vegreferanse{}.Vegreferanse.veglenkeMeterFra xml_char(200), assosiertObjekt.vegreferanse{}.Vegreferanse.veglenkeMeterTil xml_char(200), assosiertObjekt.vegreferanse{}.Vegreferanse.referanseretning xml_char(200), assosiertObjekt.vegreferanse{}.Vegreferanse.vegreferanseFraDato xml_char(200), assosiertObjekt.vegreferanse{}.Vegreferanse.vegreferanseTilDato xml_char(200), assosiertObjekt.bruksområde xml_char(200), assosiertObjekt.type xml_char(200), assosiertObjekt.navnPåStrekning xml_char(200),
      assosiertObjekt.byggeår xml_char(200), assosiertObjekt.tenningssystem xml_char(200), assosiertObjekt.dimming xml_char(200), assosiertObjekt.fjernstyring xml_char(200), assosiertObjekt.avstandInnbyrdes xml_char(200), assosiertObjekt.luminansnivå xml_char(200), assosiertObjekt.eier xml_char(200), assosiertObjekt.eierNavn xml_char(200), assosiertObjekt.vedlikeholdsansvarlig xml_char(200), assosiertObjekt.senterlinje xml_char(200), assosiertObjekt.lineærPosisjon{}.LineærPosisjonStrekning.lineærReferanseMetode xml_char(200), assosiertObjekt.lineærPosisjon{}.LineærPosisjonStrekning.retning xml_char(200), assosiertObjekt.lineærPosisjon{}.LineærPosisjonStrekning.avstandSide xml_char(200), assosiertObjekt.lineærPosisjon{}.LineærPosisjonStrekning.fraPosisjon xml_char(200), assosiertObjekt.lineærPosisjon{}.LineærPosisjonStrekning.tilPosisjon xml_char(200), assosiertObjekt.assosiertKommentar{}.owns xml_char(200), assosiertObjekt.assosiertKommentar{}.nilReason xml_char(200), assosiertObjekt.assosiertKommentar{}.gml_remoteSchema xml_char(200), assosiertObjekt.assosiertKommentar{}.xlink_href xml_char(200), assosiertObjekt.assosiertDokumentasjon{}.owns xml_char(200), assosiertObjekt.assosiertDokumentasjon{}.nilReason xml_char(200), assosiertObjekt.assosiertDokumentasjon{}.gml_remoteSchema xml_char(200), assosiertObjekt.assosiertDokumentasjon{}.xlink_href xml_char(200), assosiertObjekt.assosiertBelysningspunkt{}.owns xml_char(200), assosiertObjekt.assosiertBelysningspunkt{}.nilReason xml_char(200), assosiertObjekt.assosiertBelysningspunkt{}.gml_remoteSchema xml_char(200), assosiertObjekt.assosiertBelysningspunkt{}.xlink_href xml_char(200), assosiertObjekt.fme_feature_type xml_char(200), assosiertObjekt.gml_parent_id xml_char(200), assosiertObjekt.gml_parent_property xml_char(200),
      assosiertObjekt.gml_id xml_char(200), assosiertObjekt.ftid xml_char(200), assosiertObjekt._matched_records xml_char(200), assosiertObjekt.xlink_href xml_char(200), _assosiasjonsliste{}.identifikasjon.Identifikasjon.lokalId xml_char(200), _assosiasjonsliste{}.identifikasjon.Identifikasjon.navnerom xml_char(200), _assosiasjonsliste{}.identifikasjon.Identifikasjon.versjonId xml_char(200), _assosiasjonsliste{}.endringsflagg.Endringsflagg.typeEndring xml_char(200), _assosiasjonsliste{}.endringsflagg.Endringsflagg.tidspunktEndring xml_char(200), _assosiasjonsliste{}.datafangstdato xml_char(200), _assosiasjonsliste{}.oppdateringsdato xml_char(200), _assosiasjonsliste{}.kvalitet.Posisjonskvalitet.målemetode xml_char(200), _assosiasjonsliste{}.kvalitet.Posisjonskvalitet.nøyaktighet xml_char(200), _assosiasjonsliste{}.kvalitet.Posisjonskvalitet.synbarhet xml_char(200), _assosiasjonsliste{}.kvalitet.Posisjonskvalitet.målemetodeHøyde xml_char(200), _assosiasjonsliste{}.kvalitet.Posisjonskvalitet.nøyaktighetHøyde xml_char(200), _assosiasjonsliste{}.kvalitet.Posisjonskvalitet.maksimaltAvvik xml_char(200), _assosiasjonsliste{}.prosesshistorie xml_char(200), _assosiasjonsliste{}.høydereferanse xml_char(200), _assosiasjonsliste{}.kommunenummer xml_char(200), _assosiasjonsliste{}.sideposisjon xml_char(200), _assosiasjonsliste{}.vegreferanse{}.Vegreferanse.vegkategori xml_char(200), _assosiasjonsliste{}.vegreferanse{}.Vegreferanse.vegstatus xml_char(200), _assosiasjonsliste{}.vegreferanse{}.Vegreferanse.vegnummer xml_char(200), _assosiasjonsliste{}.vegreferanse{}.Vegreferanse.hovedParsell xml_char(200), _assosiasjonsliste{}.vegreferanse{}.Vegreferanse.veglenkeMeterFra xml_char(200), _assosiasjonsliste{}.vegreferanse{}.Vegreferanse.veglenkeMeterTil xml_char(200), _assosiasjonsliste{}.vegreferanse{}.Vegreferanse.referanseretning xml_char(200), _assosiasjonsliste{}.vegreferanse{}.Vegreferanse.vegreferanseFraDato xml_char(200), _assosiasjonsliste{}.vegreferanse{}.Vegreferanse.vegreferanseTilDato xml_char(200),
      _assosiasjonsliste{}.bruksområde xml_char(200), _assosiasjonsliste{}.type xml_char(200), _assosiasjonsliste{}.navnPåStrekning xml_char(200), _assosiasjonsliste{}.byggeår xml_char(200), _assosiasjonsliste{}.tenningssystem xml_char(200), _assosiasjonsliste{}.dimming xml_char(200), _assosiasjonsliste{}.fjernstyring xml_char(200), _assosiasjonsliste{}.avstandInnbyrdes xml_char(200), _assosiasjonsliste{}.luminansnivå xml_char(200), _assosiasjonsliste{}.eier xml_char(200), _assosiasjonsliste{}.eierNavn xml_char(200), _assosiasjonsliste{}.vedlikeholdsansvarlig xml_char(200), _assosiasjonsliste{}.senterlinje xml_char(200), _assosiasjonsliste{}.lineærPosisjon{}.LineærPosisjonStrekning.lineærReferanseMetode xml_char(200), _assosiasjonsliste{}.lineærPosisjon{}.LineærPosisjonStrekning.retning xml_char(200), _assosiasjonsliste{}.lineærPosisjon{}.LineærPosisjonStrekning.avstandSide xml_char(200), _assosiasjonsliste{}.lineærPosisjon{}.LineærPosisjonStrekning.fraPosisjon xml_char(200), _assosiasjonsliste{}.lineærPosisjon{}.LineærPosisjonStrekning.tilPosisjon xml_char(200), _assosiasjonsliste{}.assosiertKommentar{}.owns xml_char(200), _assosiasjonsliste{}.assosiertKommentar{}.nilReason xml_char(200), _assosiasjonsliste{}.assosiertKommentar{}.gml_remoteSchema xml_char(200), _assosiasjonsliste{}.assosiertKommentar{}.xlink_href xml_char(200), _assosiasjonsliste{}.assosiertDokumentasjon{}.owns xml_char(200), _assosiasjonsliste{}.assosiertDokumentasjon{}.nilReason xml_char(200), _assosiasjonsliste{}.assosiertDokumentasjon{}.gml_remoteSchema xml_char(200), _assosiasjonsliste{}.assosiertDokumentasjon{}.xlink_href xml_char(200), _assosiasjonsliste{}.assosiertBelysningspunkt{}.owns xml_char(200), _assosiasjonsliste{}.assosiertBelysningspunkt{}.nilReason xml_char(200), _assosiasjonsliste{}.assosiertBelysningspunkt{}.gml_remoteSchema xml_char(200), _assosiasjonsliste{}.assosiertBelysningspunkt{}.xlink_href xml_char(200),
      _assosiasjonsliste{}.fme_feature_type xml_char(200), _assosiasjonsliste{}.gml_parent_id xml_char(200), _assosiasjonsliste{}.gml_parent_property xml_char(200), _assosiasjonsliste{}.gml_id xml_char(200), _assosiasjonsliste{}.ftid xml_char(200), _assosiasjonsliste{}._matched_records xml_char(200), _assosiasjonsliste{}.xlink_href xml_char(200)

Bookmark: Liste med objekttyper som skal endres til attributter på andre objekttyper
Creator
    GEOMTYPE = Geometry Object
    NUM = 1
    CREATED -> AttributeManager
AttributeManager
    ATTR_TABLE:
      REMOVE _creation_instance
      SET_TO ftids = $(ftIDxtra)
    -> AttributeSplitter
AttributeSplitter
    TRIM_OPTION = Both
    ATTR_NAME = ftids
    DELIMITER = ;
    LIST_NAME = _ftidList
    DROP_EMPTY_PARTS = No
    -> ListExploder
ListExploder
    ATTR_CONFLICT_RES = Use Incoming List
    LIST_ATTR = _ftidList{}
    INDEX_ATTR = _element_index
    ATTR_ACCUM_MODE = Merge Incoming List
    ELEMENTS -> AttributeManager_2
AttributeManager_2
    ATTR_TABLE:
      REMOVE ftids
      RENAME_SET_VALUE _ftidList > ftid
      REMOVE _element_index
    -> FeatureMerger [SUPPLIER]
