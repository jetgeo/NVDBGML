FME workspace xml2none.fmw

Parameters:
- SourceDataset_XML = C:\DATA\GitHub\NVDBGML\API\lenker.xml   # Source XML File(s)
- namespace = vegvesen.no.nvdb   # Namespace

Readers:
- XML_1: XML from $(SourceDataset_XML)

lenke (reader XML_1)
    attributes: felt xml_char(4), fylke xml_decimal(2,0), geometri.kvalitet.datafangstdato xml_char(11), geometri.kvalitet.høydemetode xml_decimal(3,0), geometri.kvalitet.høydenøyaktighet xml_decimal(3,0), geometri.kvalitet.metode xml_decimal(3,0), geometri.kvalitet.nøyaktighet xml_decimal(4,0), geometri.kvalitet.synlighet xml_decimal(3,0), geometri.kvalitet.toleranse xml_decimal(3,0), geometri.srid xml_decimal(6,0), geometri.wkt xml_char(1580), href xml_char(59), kommune xml_decimal(4,0), konnekteringslenke xml_char(6), kortform xml_char(47), medium xml_char(2), metadata.startdato xml_char(11), region xml_decimal(2,0), sluttnode xml_char(11), sluttposisjon xml_decimal(19,17), startnode xml_char(11), startposisjon xml_decimal(19,17), strekningslengde xml_decimal(5,0), vegavdeling xml_decimal(2,0), veglenkeid xml_decimal(8,0), vegreferanse.fra_meter xml_decimal(5,0), vegreferanse.fylke xml_decimal(2,0), vegreferanse.hp xml_decimal(2,0), vegreferanse.kategori xml_char(2), vegreferanse.kommune xml_decimal(4,0),
      vegreferanse.kortform xml_char(28), vegreferanse.nummer xml_decimal(6,0), vegreferanse.status xml_char(2), vegreferanse.til_meter xml_decimal(5,0), xml_fragment xml_xml, xml_id xml_char(16), xml_matched_element xml_char(6), xml_parent_child_pos xml_char(1), xml_parent_id xml_char(1)
    -> NVDBTranslator
Note: Oversetter fra NVDB-API-XML
NVDBTranslator: PythonCaller
    PYTHONSYMBOL = extractNVDB_XML
    PYTHONSOURCE:
      import fme
      import fmeobjects

      def extractNVDB_XML(feature):

          ns=FME_MacroValues['namespace']

          # Setter feature type
          ft='veglenke'
          # ID og versjon
          feature.setAttribute('identifikasjon.Identifikasjon.navnerom', ns)
          v=feature.getAttribute('veglenkeid')
          feature.setAttribute('NVDB_ID', v)
          feature.setAttribute('identifikasjon.Identifikasjon.lokalId', v)
          feature.setAttribute('gml_id', ns + '.' + v)
          feature.removeAttribute('veglenkeid')

          #LR-info
          feature.setAttribute('standardLRM', 'normalisert')
          #'startposisjon og sluttposisjon er korrekt fra API :)

          #Topologi
          #detaljnivå
          #    <topologinivå>1</topologinivå>
          #    <topologinivå_tekst>Kjørebane</topologinivå_tekst>
          v=feature.getAttribute('topologinivå')
          if v != None:
              #print v
              if v == '0':
                  feature.setAttribute('detaljnivå', 'vegtrase')
              if v == '1':
                  feature.setAttribute('detaljnivå', 'kjørebane')
              if v == '2':
                  feature.setAttribute('detaljnivå', 'kjørefelt')
              feature.removeAttribute('topologinivå_tekst')
             #feature.removeAttribute('topologinivå')

          #noder
          #    <startnode>2373197-1</startnode>
          v=str(feature.getAttribute('startnode'))
          if v != 'None':
              #feature.removeAttribute('startnode')
              feature.setAttribute('startnode.xlink:href', 'Noder.gml#' + ns + '.' + v)
          #    <sluttnode>1087601-2</sluttnode>
          v=str(feature.getAttribute('sluttnode'))
          if v != 'None':
              #feature.removeAttribute('sluttnode')
              feature.setAttribute('sluttnode.xlink:href', 'Noder.gml#' + ns + '.' + v)

          #medium
          #    <medium>T</medium> er riktig :*)
          #konnekteringslenke
          #    <konnekteringslenke>false</konnekteringslenke> er riktig :)

          #Kvalitet
          #            <metode>60</metode>
          v=str(feature.getAttribute('geometri.kvalitet.metode'))
          if v != 'None' and v != '-1':
              feature.setAttribute('kvalitet.Posisjonskvalitet.målemetode', v)
          feature.removeAttribute('geometri.kvalitet.metode')
          #            <nøyaktighet>200</nøyaktighet>
          v=str(feature.getAttribute('geometri.kvalitet.nøyaktighet'))
          if v != 'None' and v != '-1':
              feature.setAttribute('kvalitet.Posisjonskvalitet.nøyaktighet', v)
          feature.removeAttribute('geometri.kvalitet.nøyaktighet')
          #            <høydenøyaktighet>-1</høydenøyaktighet>
          v=str(feature.getAttribute('geometri.kvalitet.høydenøyaktighet'))
          if v != 'None' and v != '-1':
              feature.setAttribute('kvalitet.Posisjonskvalitet.nøyaktighetHøyde', v)
          feature.removeAttribute('geometri.kvalitet.høydenøyaktighet')
          #            <toleranse>-1</toleranse>
          v=str(feature.getAttribute('geometri.kvalitet.toleranse'))
          if v != 'None' and v != '-1':
              feature.setAttribute('maksimaltAvvik', v)
          feature.removeAttribute('kvalitet.Posisjonskvalitet.geometri.kvalitet.toleranse')
          #            <synlighet>99</synlighet>
          v=str(feature.getAttribute('geometri.kvalitet.synlighet'))
          if v != 'None' and v != '-1':
              feature.setAttribute('kvalitet.Posisjonskvalitet.synlighet', v)
          feature.removeAttribute('geometri.kvalitet.synlighet')
          #            <datafangstdato>2002-12-07</datafangstdato>
          v=str(feature.getAttribute('geometri.kvalitet.datafangstdato'))
          if v != 'None' and v != '-1':
              feature.setAttribute('datafangstdato', v)
          feature.removeAttribute('geometri.kvalitet.datafangstdato')

          # Geometri
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')
    NEW_ATTRIBUTES = geometri fme_feature_type identifikasjon.Identifikasjon.lokalId identifikasjon.Identifikasjon.versjonId identifikasjon.Identifikasjon.navnerom gml_id epsg detaljnivå startnode sluttnode
    -> GeometryReplacer
Note: Geometri
GeometryReplacer
    SOURCE = @Value(geometri)
    REMOVE_ATTRIBUTE = Yes
    OGC_WKT_PRECISION_DISPLAY = 64-bit
    KIND_LONG = OGC Well Known Text
    -> CoordinateSystemSetter
    -> CoordinateSystemSetter_2
CoordinateSystemSetter
    COORDSYS = @Value(epsg)
    -> CoordinateSystemSetter_Output
CoordinateSystemSetter_Output: Inspector
    TACKATTRS = detaljnivå
CoordinateSystemSetter_2 [off]
    COORDSYS = EPSG:25833
