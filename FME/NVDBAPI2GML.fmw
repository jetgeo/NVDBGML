FME workspace NVDBAPI2GML.fmw

Parameters:
- gmlName = Drenering   # GML file and schema name
- ftID = 78,79,83   # NVDB feature type ID
- Kommuner = 519   # komm
- xsdFolder = C:\DATA\Standardisering\NVDBGML\XSD   # XSD Main folder
- gmlFolder = C:\DATA\Standardisering\NVDBGML\GML   # Output GML folder
- gmlNamespace = https://raw.githubusercontent.com/jetgeo/NVDBGML/master/XSD   # GML Namespace
- xfmap_api = $(FME_MF_DIR)API_Mapping.xmp   # xfMap for API-mapping
- xfmap_xsd = $(FME_MF_DIR)NVDB_GML_SchemaMapper.xmp   # xfMap for XSD
- coordsys = EPSG:25833   # Koordinatsystem
- namespace = vegvesen.no.nvdb   # Attribute Value
- xsdLocalComplete:   # Python Script
      xsdLC = FME_MacroValues['xsdFolder'] + '\\' + FME_MacroValues['gmlName'] + '.xsd'
      #Debug
      #print xsdLC
      return xsdLC
- gmlComplete:   # Python Script
      gmlLC = FME_MacroValues['gmlFolder'] + '\\' + FME_MacroValues['gmlName'] + '.gml'
      #Debug
      #print gmlLC
      return gmlLC
- maxFeatures = 10000   # Maximal number of features

Writers:
- GML_1: GML to $(gmlComplete)

Creator
    NUM = 1
    GEOMTYPE = Geometry Object
    CREATED -> AttributeCreator_3
AttributeCreator_3
    ATTR_LIST = ftID,$(ftID)
    -> AttributeSplitter
AttributeSplitter
    ATTR_NAME = ftID
    DELIMITER = ,
    DROP_EMPTY_PARTS = No
    TRIM_OPTION = Both
    LIST_NAME = _ftID
    -> ListExploder
ListExploder
    LIST_ATTR = _ftID{}
    INDEX_ATTR = _element_index
    ATTR_CONFLICT_RES = Use Original
    ATTR_ACCUM_MODE = Merge Incoming List
    LIST_FOUND -> AttributeCreator
    LIST_FOUND -> AttributeCreator_2
    NOT_FOUND -> AttributeCreator_2
    NOT_FOUND -> AttributeCreator
Note: Kunne hente alle objekttyper fra et gitt applikasjonsskjema? / - Lese alle objekttyper i et applikasjonsskjema, med ID, og sende disse til API
Note: AttributeCreator [AttributeCreator:6] / DISABLED / Number of Prior Features: 0 / Number of Subsequent Features: 0 / _api = https://www.vegvesen.no/nvdb/api/sok?kriterie={objektTyper:[{id:@Value(_ftID),antall:$(maxFeatures)}]} / _gmlFeatureType = $(gmlName) / Version: 6 / Last Parameter Edit: Build 15479
AttributeCreator [off]
    ATTR_LIST = _api,https://www.vegvesen.no/nvdb/api/sok?kriterie={objektTyper:[{id:@Value(_ftID),antall:$(maxFeatures)}]},_gmlFeatureType,$(gmlName)
    NUM_PRIOR_FEATURES = 0
    NUM_SUBSEQUENT_FEATURES = 0
    -> NVDBAPI2GML
Note: AttributeCreator_2 [AttributeCreator:6] / Number of Prior Features: 0 / Number of Subsequent Features: 0 / _api = https://www.vegvesen.no/nvdb/api/sok?kriterie={lokasjon:{kommune: [$(Kommuner)]},objektTyper:[{id:@Value(_ftID),antall:$(maxFeatures)}]} / Version: 6 / Last Parameter Edit: Build 15479
AttributeCreator_2
    ATTR_LIST = _api,https://www.vegvesen.no/nvdb/api/sok?kriterie={lokasjon:{kommune: [$(Kommuner)]},objektTyper:[{id:@Value(_ftID),antall:$(maxFeatures)}]}
    NUM_PRIOR_FEATURES = 0
    NUM_SUBSEQUENT_FEATURES = 0
    -> NVDBAPI2GML
NVDBAPI2GML
    apiString = @Value(_api)
    xfmap_api = $(xfmap_api)
    coordsys = $(coordsys)
    xsd = $(xsdLocalComplete)
    xfmap_xsd = $(xfmap_xsd)
    namespace = $(namespace)
    -> Vegobjekttype (writer GML_1)
Vegobjekttype (writer GML_1)
    attributes: _creation_instance xml_char(200), ftID xml_char(200), _ftID xml_char(200), _element_index xml_char(200), _api xml_char(200), _gmlFeatureType xml_char(200), _headers{}.name xml_char(200), _headers{}.value xml_char(200), _error xml_char(200), _http_status_code xml_char(200), _url_contents xml_char(200), egengeometri xml_char(200), vegreferanse{}.vegkategori xml_char(200), vegreferanse{}.vegnummer xml_char(200), vegreferanse{}.vegstatus xml_char(200), vegreferanse{}.hovedParsell xml_char(200), vegreferanse{}.veglenkeMeterFra xml_char(200), vegreferanse{}.veglenkeMeterTil xml_char(200), _xml_feature_count_ xml_char(200), _xml_source_ xml_char(200), _schemamapper_row_ids xml_char(200), prosesshistorie xml_char(200), identifikasjon.Identifikasjon.lokalId xml_buffer, identifikasjon.Identifikasjon.navnerom xml_buffer, lineærPosisjon.LineærPosisjonPunkt.lineærtObjektIdentifikasjon.Identifikasjon.lokalId xml_char(200), lineærPosisjon.LineærPosisjonPunkt.posisjon xml_char(200), lineærPosisjon.LineærPosisjonPunkt.tilPosisjon xml_char(200), lineærPosisjon.LineærPosisjonPunkt.felt xml_char(200), _element_count xml_char(200), lineærPosisjon.LineærPosisjonPunkt.lineærtObjektIdentifikasjon.Identifikasjon.navnerom xml_char(200),
      lineærPosisjon{}.LineærPosisjonStrekning.lineærtObjektIdentifikasjon.Identifikasjon.lokalId xml_char(200), lineærPosisjon{}.LineærPosisjonStrekning.fraPosisjon xml_char(200), lineærPosisjon{}.LineærPosisjonStrekning.tilPosisjon xml_char(200), lineærPosisjon{}.LineærPosisjonStrekning.felt xml_char(200), lineærPosisjon{}.identifikasjon.Identifikasjon.lokalId xml_char(200), lineærPosisjon{}._element_count xml_char(200), lineærPosisjon{}._element_index xml_char(200), lineærPosisjon{}.LineærPosisjonStrekning.lineærtObjektIdentifikasjon.Identifikasjon.navnerom xml_char(200)

FME custom transformer NVDBAPI2GML

Parameters:
- apiString = @Value(_api)   # Tekst med kall til API
- xsd = C:\DATA\Standardisering\NVDBGML\XSD\Drenering.xsd   # xsd-fil
- xfmap_api = $(FME_MF_DIR)API_Mapping.xmp   # xfMap for API-mapping
- xfmap_xsd = $(FME_MF_DIR)NVDB_GML_SchemaMapper.xmp   # xfMap for XSD
- namespace = vegvesen.no.nvdb   # Attribute Value
- coordsys = EPSG:25833   # Koordinatsystem

Input (input)
    -> HTTPFetcher_2
Note: Henter objekter fra NVDB-API
HTTPFetcher_2
    VERIFY_SSL_CERTIFICATES = Yes
    USE_COOKIES = No
    RESPONSE_HEADER_LIST_ATTR = _headers
    STATUS_CODE_ATTR = _http_status_code
    ERROR_ATTR = _error
    PROXY_AUTH_METHOD = Basic
    FOLLOW_REDIRECTS = Yes
    REQUEST_HEADER:
      GET /vegobjekter HTTP/1.1
      Accept: application/vnd.vegvesen.nvdb-v1+xml
    AUTH_METHOD = Basic
    TARGET_ATTR = _url_contents
    TARGET_URL = @Value(_api)
    SAVE_FILE = No
    -> XMLFeatureMapper
Note: Tolker XML
XMLFeatureMapper
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt
    XML_INPUT_TYPE = Attribute with XML document
    XML_SOURCE_NAME = _xml_source_
    ATTRIBUTE_XML = _url_contents
    SINGLE_XFMAP = $(xfmap_api)
    MERGE_ATTRS = Yes
    CONFIGURATION_TYPE = Single xfMap file
    FEATURE_TYPE_ATTR = fme_feature_type
    FEATURE_COUNT_PER_XML = _xml_feature_count_
    MAPPED -> GeometryReplacer
Note: Tildeler geometri
GeometryReplacer
    SOURCE = @Value(geometriUtm33)
    KIND_LONG = OGC Well Known Text
    REMOVE_ATTRIBUTE = Yes
    -> CoordinateSystemSetter
CoordinateSystemSetter
    COORDSYS = $(coordsys)
    -> SchemaMapper
Note: Mapper egenskapsnavn til GML, vha applikasjonsskjemaet
SchemaMapper
    XML_XFMAP = $(xfmap_xsd)
    IDXDESTCOL = ""
    IDXSOURCEATTR = fme_feature_type
    FORMAT = XML
    TABLE = element
    XML_FILE_TYPE = xfMap
    XML_USE_HTTP_AUTH = NO
    XML_CLIP_TO_ENVELOPE = NO
    IDXSOURCECOL = ""
    IDXDESTATTR = fme_feature_type
    XML_CONTINUE_ON_GEOM_ERROR = yes
    DATASET = $(xsd)
    MAP_ATTRS = NVDB_ID name """"""
    ROW_ID_ATTR = _schemamapper_row_ids
    MAPPED -> NullAttributeMapper_3
NullAttributeMapper_3
    ATTRCHOICE = All Attributes
    NULL_TREATMENT = Missing
    SOURCE_ATTR_VAL = Empty Null
    -> SchemaMapper_3
Note: Mapperobjekttypenavn til GML, vha applikasjonsskjemaet
SchemaMapper_3
    XML_CONTINUE_ON_GEOM_ERROR = yes
    IDXDESTCOL = name
    FORMAT = XML
    XML_CLIP_TO_ENVELOPE = NO
    IDXSOURCEATTR = fme_feature_type
    IDXDESTATTR = fme_feature_type
    ROW_ID_ATTR = _schemamapper_row_ids
    XML_FILE_TYPE = xfMap
    XML_XFMAP = $(xfmap_xsd)
    DATASET = $(xsd)
    TABLE = element
    XML_USE_HTTP_AUTH = NO
    IDXSOURCECOL = NVDB_ID
    MAPPED -> GeometryFilter
AttributeValueMapper_2
    VAL_ATTR = prosesshistorie
    LUT = true,Geometri: Egengeometri fra NVDB
    DIRECTION = Forward (Source To Destination)
    SRC = egengeometri
    DEFAULT_VALUE = Geometri: Generert fra lineære referanser til vegnett i NVDB
    -> AttributeExposer_2
AttributeExposer_2
    ATTR_LIST = NVDB_ID
    -> AttributeRenamer_3
Note: ID
AttributeRenamer_3
    ATTR_LIST = NVDB_ID,identifikasjon.Identifikasjon.lokalId,"","",identifikasjon.Identifikasjon.navnerom,$(namespace)
    -> AttributeKeeper
    -> AttributeRemover
AttributeRemover
    LIST_ATTRS = lineærPosisjon{}
    -> FeatureMerger [input 1]
AttributeKeeper
    KEEP_ATTRS = identifikasjon.Identifikasjon.lokalId
    KEEP_LIST = lineærPosisjon{}.felt lineærPosisjon{}.fraPosisjon lineærPosisjon{}.tilPosisjon lineærPosisjon{}.lineærtObjektIdentifikasjon.Identifikasjon.lokalId
    -> ListElementCounter
ListElementCounter
    CNT_ATTR = _element_count
    LIST_NAME = lineærPosisjon{}
    -> TestFilter
TestFilter
    TEST_LIST:
      BOOL_OP,AND,COMPOSITE_TEST,<Unused>,TEST_CLAUSE,"TEST @Value(lineærPosisjon{0}.fraPosisjon) = @Value(lineærPosisjon{0}.tilPosisjon)
      TEST @Value(_element_count) = 1",Punkt
    DEFAULT_VALUE = Strekning
    Punkt -> ListExploder
    Strekning -> ListExploder_2
FeatureMerger
    SUPPLIERS_FIRST = No
    PROCESS_DUPS = No
    ATTR_ACCUM_MODE = Merge Supplier
    IGNORE_NULLS = No
    JOIN_KEYS = @Value(identifikasjon.Identifikasjon.lokalId) @Value(identifikasjon.Identifikasjon.lokalId) AUTO
    MERGE_TYPE = Attributes Only
    ATTR_CONFLICT_RES = Use Requestor
    MERGED -> AttributeCreator_2
    NOT_MERGED -> AttributeCreator_2
AttributeCreator_2
    ATTR_LIST = gml_id,$(namespace).@Value(identifikasjon.Identifikasjon.lokalId)
    -> Output (output)
Output (output)

Bookmark: Definerer geometriegenskaper
GeometryFilter
    BREAK_AGG = No
    GEOM_PORT_NAMES = Point Line Area
    POINT -> GeometryPropertySetter
    LINE -> GeometryPropertySetter_2
    AREA -> GeometryPropertySetter_3
GeometryPropertySetter
    SETTYPE_PARAM = Geometry Name
    OVERWRITE_CHOICE = Yes
    GEOM_NAME_FIELD = posisjon
    SET -> AttributeValueMapper_2
GeometryPropertySetter_2
    SETTYPE_PARAM = Geometry Name
    OVERWRITE_CHOICE = Yes
    GEOM_NAME_FIELD = senterlinje
    SET -> AttributeValueMapper_2
GeometryPropertySetter_3
    SETTYPE_PARAM = Geometry Name
    OVERWRITE_CHOICE = Yes
    GEOM_NAME_FIELD = område
    SET -> AttributeValueMapper_2

Bookmark: Lager lineærPosisjon (punkt)
ListExploder
    LIST_ATTR = lineærPosisjon{}
    INCOMING_PREFIX = lineærPosisjon.LineærPosisjonPunkt.
    INDEX_ATTR = _element_index
    ATTR_ACCUM_MODE = Prefix Incoming List
    LIST_FOUND -> AttributeRenamer
AttributeRenamer
    ATTR_LIST = lineærPosisjon.LineærPosisjonPunkt.fraPosisjon,lineærPosisjon.LineærPosisjonPunkt.posisjon,,,lineærPosisjon.LineærPosisjonPunkt.lineærtObjektIdentifikasjon.Identifikasjon.navnerom,$(namespace).rl
    -> FeatureMerger [input 2]

Bookmark: Lager lineærPosisjon-liste (strekning)
ListExploder_2
    LIST_ATTR = lineærPosisjon{}
    INCOMING_PREFIX = LineærPosisjonStrekning.
    INDEX_ATTR = _element_index
    ATTR_ACCUM_MODE = Prefix Incoming List
    LIST_FOUND -> AttributeCreator
AttributeCreator
    ATTR_LIST = LineærPosisjonStrekning.lineærtObjektIdentifikasjon.Identifikasjon.navnerom,$(namespace).rl
    -> ListBuilder
ListBuilder
    GRP_BY = identifikasjon.Identifikasjon.lokalId
    LIST_NAME = lineærPosisjon
    -> FeatureMerger [input 2]
