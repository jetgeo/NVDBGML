FME workspace GML2NVDB.fmw

Parameters:
- SourceDataset_GML = C:\DATA\Standardisering\NVDBGML\GML\InnmålteStikkrennerMGD.gml   # Source Geography Markup Language (GML) File(s)
- SourceDataset_XML = C:\DATA\Standardisering\NVDBGML\XSD\Stikkrenne.xsd   # Source XML File(s)

Readers:
- GML_1: GML from $(SourceDataset_GML)
- XML_1: XML from $(SourceDataset_XML)

Stikkrenne (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer, bruksområde xml_buffer,
      senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
    -> SchemaMapper
Note: Mapper objekttypenavn til VOT-ID, vha applikasjonsskjemaet
SchemaMapper
    XML_XFMAP = $(FME_MF_DIR)NVDB_GML_SchemaMapper.xmp
    XML_CLIP_TO_ENVELOPE = NO
    XML_FILE_TYPE = xfMap
    ROW_ID_ATTR = _schemamapper_row_ids
    XML_CONTINUE_ON_GEOM_ERROR = yes
    IDXDESTCOL = NVDB_ID
    IDXSOURCECOL = name
    TABLE = element
    DATASET = C:\DATA\Standardisering\NVDBGML\XSD\Stikkrenne.xsd
    XML_USE_HTTP_AUTH = NO
    FORMAT = XML
    IDXSOURCEATTR = fme_feature_type
    IDXDESTATTR = fme_feature_type
    MAPPED -> Stikkrenne
    MAPPED -> SchemaMapper_2
Stikkrenne: Inspector
Note: Mapper egenskapsnavn til ET-ID, vha applikasjonsskjemaet / Mangler: Filter på objekttype for å få riktig kobling ved like navn
SchemaMapper_2
    MAP_ATTRS = name NVDB_ID $(FME_ASC_16)
    XML_XFMAP = $(FME_MF_DIR)NVDB_GML_SchemaMapper.xmp
    XML_CLIP_TO_ENVELOPE = NO
    XML_FILE_TYPE = xfMap
    ROW_ID_ATTR = _schemamapper_row_ids
    XML_CONTINUE_ON_GEOM_ERROR = yes
    IDXDESTCOL = ""
    IDXSOURCECOL = ""
    TABLE = element
    DATASET = C:\DATA\Standardisering\NVDBGML\XSD\Stikkrenne.xsd
    XML_USE_HTTP_AUTH = NO
    FORMAT = XML
    IDXSOURCEATTR = fme_feature_type
    IDXDESTATTR = fme_feature_type
    MAPPED -> SchemaMapper_2_Mapped
    UNMAPPED -> SchemaMapper_2_Unmapped
SchemaMapper_2_Mapped: Inspector
SchemaMapper_2_Unmapped: Inspector
element (reader XML_1) [off]
    attributes: NVDB_ID xml_decimal(6,0), name xml_char(26)
    -> element
element: Inspector
