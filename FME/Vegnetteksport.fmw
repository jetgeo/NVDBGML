FME workspace Vegnetteksport.fmw

Parameters:
- knr = 519   # Kommunenummer
- detaljNivå = Kjørefelt   # Detaljnivå

Creator_2
    NUM = 1
    GEOMTYPE = Geometry Object
    CREATED -> StringConcatenator_6
StringConcatenator_6
    VAL_ATTR = _kommunewhere
    PARM_LINE = KOMM=$(knr)
    -> FeatureReader
FeatureReader
    FEATURETYPES = N250_AdminFlate
    DATASET = K:\Vektor\00\23-N250\00\EsriGDB\N250.gdb
    GEODATABASE_FILE_SPLIT_COMPLEX_EDGES = no
    COMBINE_ATTRS = Keep result attributes only
    ATTRIBUTES = N250_AdminFlate,"geodb_oid,OBJECTID,OBJTYPE,NAVN,KOMM,OPPDATERINGSDATO,Shape_Length,Shape_Area"
    FORMAT = GEODATABASE_FILE
    GEODATABASE_FILE_SPLIT_MULTI_PART_ANNOS = no
    GEODATABASE_FILE_IGNORE_NETWORK_INFO = yes
    GEODATABASE_FILE_TABLELIST = N250_AdminFlate
    GEODATABASE_FILE_IGNORE_RELATIONSHIP_INFO = yes
    GEODATABASE_FILE_TRANSLATE_SPATIAL_DATA_ONLY = no
    SUPPORTED_SPATIAL_INTERACTIONS = ENVELOPE_INTERSECT%INTERSECTS%CONTAINS%CROSSES%DISJOINT%EQUALS%OVERLAPS%TOUCHES%WITHIN
    GEODATABASE_FILE_RESOLVE_SUBTYPE_NAMES = yes
    COMBINE_GEOM = Keep result geometry only
    WHERE = @Value(_kommunewhere)
    GEODATABASE_FILE_FEATURE_READ_MODE = Features
    GEODATABASE_FILE_RESOLVE_DOMAINS = no
    N250_AdminFlate -> Dissolver
Dissolver
    ACCUM_INPUT_ATTRS = No
    NO_OVRLP = No
    AREA -> DonutHoleExtractor
DonutHoleExtractor
    OUTERSHELL -> FeatureReader_2
Note: CurveSegment, RefLinkPart og RefNode
FeatureReader_2
    GEODATABASE_SDE_FEATURE_READ_MODE = Features
    GEODATABASE_SDE_RESOLVE_DOMAINS = no
    GEODATABASE_SDE_SPLIT_MULTI_PART_ANNOS = no
    COMBINE_GEOM = Use Result
    GEODATABASE_SDE_ALIAS_MODE = NONE
    GEODATABASE_SDE_CLIP_TO_ENVELOPE = NO
    GEODATABASE_SDE_SPLIT_COMPLEX_ANNOS = no
    GEODATABASE_SDE_TRANSLATE_SPATIAL_DATA_ONLY = no
    GEODATABASE_SDE_CREDENTIALS_OVERRIDE = NO
    SUPPORTED_SPATIAL_INTERACTIONS = ENVELOPE_INTERSECT%INTERSECTS%CONTAINS%CROSSES%DISJOINT%EQUALS%OVERLAPS%TOUCHES%WITHIN
    WHERE = TO_DATE = 99991231
    GEODATABASE_SDE_PERSISTENT_CONNECTION = no
    GEODATABASE_SDE_CACHE_MULTIPATCH_TEXTURES = yes
    GEODATABASE_SDE_IGNORE_NETWORK_INFO = yes
    GEODATABASE_SDE_REMOVE_TABLE_QUALIFIER = NO
    ATTR_ACCUM_MODE = Merge Initiator and Result
    FEATURETYPES_RADIO = FEATURETYPES
    GEODATABASE_SDE_USE_SEARCH_ENVELOPE = NO
    GEODATABASE_SDE_RESOLVE_SUBTYPE_NAMES = yes
    INTERACT = Intersects
    GEODATABASE_SDE_SEARCH_METHOD = GEODB_INTERSECTS
    GEODATABASE_SDE_SPLIT_COMPLEX_EDGES = no
    GEODATABASE_SDE_CHECK_SIMPLE_GEOM = no
    FORMAT = GEODATABASE_SDE
    GEODATABASE_SDE_CONNECTION_FILE = C:\Users\knjetl\AppData\Roaming\ESRI\Desktop10.2\ArcCatalog\PTNE-sde_tne_read@svvkartp.vegvesen.no.sde
    GEODATABASE_SDE_IGNORE_RELATIONSHIP_INFO = yes
    ATTR_CONFLICT_RES = Use Result
    GEODATABASE_SDE_SEARCH_ORDER = SPATIAL_FIRST
    GEODATABASE_SDE_QUERY_FEATURE_TYPES_FOR_MERGE_FILTERS = Yes
    FEATURETYPES = SDE_TNE.TNE_CurveSegment SDE_TNE.TNE_RefLinkPart SDE_TNE.TNE_RefNode
    ATTRIBUTES = SDE_TNE.TNE_CurveSegment,"OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,MUNICIPALITY,SHAPE.LEN",SDE_TNE.TNE_RefLinkPart,"OBJECTID,REFLINK_OID,FROM_DATE,TO_DATE,FROM_MEASURE,TO_MEASURE,FROM_REFNODE_OID,TO_REFNODE_OID,LENGTH,TOPOLOGY_LEVEL,SUPER_OID,SUPER_FROM_MEASURE,SUPER_TO_MEASURE,LANE,DIRECTION,SHAPE.LEN",SDE_TNE.TNE_RefNode,"OBJECTID,OID,VID,REFOBJ_TYPE,NEXT_FREE_PORT_NUMBER,FROM_DATE,TO_DATE"
    GEODATABASE_SDE_MERGE_FEAT_LINKED_ANNOS = no
    GEODATABASE_SDE_VERSION_OVERRIDE = NO
    SDE_TNE.TNE_RefLinkPart -> PythonCaller_3
Note: Finner valgt detaljnivå
PythonCaller_3
    NEW_ATTRIBUTES = _topoWhere
    PYTHONSYMBOL = topolevel
    PYTHONSOURCE:
      import fmeobjects

      def topolevel(feature):
          par = '0,1,2,3'
          if FME_MacroValues['detaljNivå'] == 'Vegtrase':
              par = '0,1'
          elif FME_MacroValues['detaljNivå'] == 'Kjørebane':
              par = '1,2'
          elif FME_MacroValues['detaljNivå'] == 'Kjørefelt':
              par = '1,2,3'
          feature.setAttribute("_topoWhere", par)
    -> TestFilter_4
Note: Finner lenker som skal være med
TestFilter_4
    DEFAULT_VALUE = <UNFILTERED>
    TEST_LIST = BOOL_OP,OR,COMPOSITE_TEST,<Unused>,TEST_CLAUSE,"TEST @Value(TOPOLOGY_LEVEL) IN @Value(_topoWhere)",TOPOLEVEL
    TOPOLEVEL -> TestFilter_4_TOPOLEVEL
TestFilter_4_TOPOLEVEL: Inspector
