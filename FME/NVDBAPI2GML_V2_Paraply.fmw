FME workspace NVDBAPI2GML_V2_Paraply.fmw

Parameters:
- ftIDs = 532;98;79;95   # Objekttyper
- omr = kommune   # Områdetype
- omrNvn = 403   # Område
- gmlFolder = C:\DATA\Standardisering\NVDB\GML   # GML-hovedmappe
- dwnlAssObj = Nei   # Laste ned assosierte objekter
- SourceDataset_XLSXR = S:\Oppdrag\HAM\231\55008001 E6 Arnkvern - Moelv, Veidekke\12 Modeller\01 Grunnlagsmodeller\_Arbeidsområde Geomatikk\NVDB_FKB_Objektliste\Objektliste_v_4.0\ObjektlisteNVDB.xlsm   # Source Microsoft Excel File(s)

Readers:
- XLSXR_1: XLSXR from $(SourceDataset_XLSXR)

Objekttyper ferdigvegsdata (reader XLSXR_1)
    attributes: Datasett char(22), Objekter til FKB char(31), (temakode) number(5,0), Objekter til NVDB char(27), Egenskaps-skjema char(2), Forklaring til NVDB char(256), Aktuelt i _prosjektet char(2), FKB char(14), FKB00 char(10), NVDB char(14), NVDB00 char(10), FAG char(13)
    -> TestFilter
TestFilter
    DEFAULT_VALUE = <UNFILTERED>
    TEST_LIST = BOOL_OP,OR,COMPOSITE_TEST,<Unused>,TEST_CLAUSE,"TEST @Value(Objekter til NVDB) ATTRIBUTE_HAS_VALUE """"",NVDB,BOOL_OP,OR,COMPOSITE_TEST,<Unused>,TEST_CLAUSE,"TEST @Value(Objekter til FKB) ATTRIBUTE_HAS_VALUE """"",FKB
    NVDB -> AttributeSplitter
AttributeSplitter
    ATTR_NAME = Objekter til NVDB
    DELIMITER = _
    DROP_EMPTY_PARTS = No
    LIST_NAME = _nvdb
    TRIM_OPTION = Both
    -> ListIndexer
ListIndexer
    INDEX = 1
    LIST_ATTR = _nvdb{}
    -> AttributeCreator
AttributeCreator
    ATTR_TABLE = SET_TO nvdb_objektnummer = @Value(_nvdb)
    -> ListBuilder
ListBuilder
    GROUPS_ORDERED = No
    LIST_ATTRS_TO_INCLUDE = _nvdb
    LIST_NAME = _nvdb_obj
    -> ListConcatenator
ListConcatenator
    DROP_EMPTY_PARTS = No
    LIST_ATTR = _nvdb_obj{}._nvdb
    SEP = ;
    VAL_ATTR = _nvdb_concatenated
    -> AttributeManager_3
Creator_2
    GEOMTYPE = Geometry Object
    NUM = 1
    CREATED -> AttributeManager_3
AttributeManager_3
    ATTR_TABLE:
      REMOVE _creation_instance
      SET_TO ftids = @Value(_nvdb_concatenated)
    -> AttributeSplitter_2
AttributeSplitter_2
    ATTR_NAME = ftids
    DELIMITER = ;
    DROP_EMPTY_PARTS = No
    LIST_NAME = _ftidList
    TRIM_OPTION = Both
    -> ListExploder_2
ListExploder_2
    ATTR_ACCUM_MODE = Merge List Attributes
    ATTR_CONFLICT_RES = Use List Attribute Values
    INDEX_ATTR = _element_index
    LIST_ATTR = _ftidList{}
    ELEMENTS -> AttributeManager_4
AttributeManager_4
    ATTR_TABLE:
      REMOVE ftids
      RENAME_SET_VALUE _ftidList > ftid
      REMOVE _element_index
    -> AttributeManager
AttributeManager
    ATTR_TABLE = SET_TO areas = $(omrNvn)
    -> AttributeSplitter_3
AttributeSplitter_3
    ATTR_NAME = areas
    DELIMITER = ;
    DROP_EMPTY_PARTS = No
    LIST_NAME = _areaList
    TRIM_OPTION = Both
    -> ListExploder_3
ListExploder_3
    ATTR_ACCUM_MODE = Merge List Attributes
    ATTR_CONFLICT_RES = Use List Attribute Values
    INDEX_ATTR = _element_index
    LIST_ATTR = _areaList{}
    ELEMENTS -> AttributeManager_5
AttributeManager_5
    ATTR_TABLE:
      REMOVE _element_index
      RENAME_SET_VALUE _areaList > area
    -> WorkspaceRunner
Note: API til GML-filer
WorkspaceRunner
    BLOCKING = Yes
    WORKSPACE_FILE = $(FME_MF_DIR)NVDBAPI2GML_V2_2017.fmw
    WORKSPACE_PARAMETERS = ftID,@Value(ftid),omr,$(omr),omrNvn,@Value(area),gmlFolder,$(gmlFolder),dwnlAssObj,$(dwnlAssObj)
    SUCCEEDED -> WorkspaceRunner_Succeeded
    FAILED -> WorkspaceRunner_Failed
WorkspaceRunner_Succeeded: Inspector
WorkspaceRunner_Failed: Inspector
