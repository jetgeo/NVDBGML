FME workspace gml2API.fmw

Parameters:
- SourceDataset_GML_3 = C:\DATA\NIFS\Data\0520_Stikkrenner\Validert og låst\*.gml   # Source Geography Markup Language (GML) File(s)
- DestDataset_TEXTLINE_2 = C:/DATA/NIFS/Data/0520_Stikkrenner/XML   # Destination Text File
- GML_IN_XSD_DOC_GML_4 = C:\DATA\NIFS\Modell\XSD\Stikkrenne.xsd   # NIFS-XSD
- GML_IN_XSD_DOC_GML = C:\DATA\GitHub\NVDBGML\trunk\XSD\NIFS\NVDBSK.xsd   # NVDB-XSD
- SourceDataset_GML_2 = C:\DATA\NIFS\Data\NVDB\StikkrenneKulvert.gml   # Eksistrende NVDB-data
- DestDataset_GML_3 = C:\DATA\NIFS\Data\Analyser\KoblingNVDB.gml   # Destination Geography Markup Language (GML) File
- DestDataset_GDMMAPPERSOSI_3 = C:/DATA/NIFS/Data/0520_Stikkrenner/SOSI   # SOSI_Files(*.sos) Destination SOSI 
- geomProp_2 = 5899   # Geometriegenskap
- version_2 = 2.01   # Datakatalogversjon

Readers:
- GML_1: GML from $(SourceDataset_GML_3)
- GML_2: GML from $(SourceDataset_GML_2)

Writers:
- GDMMAPPERSOSI_1: GDMMAPPERSOSI to $(DestDataset_GDMMAPPERSOSI_3) in EPSG:25833
- TEXTLINE_1: TEXTLINE to $(DestDataset_TEXTLINE_2)
- GML_3: GML to $(DestDataset_GML_3)

Note: Stikkrenne: *.gml [GML]
Stikkrenne (reader GML_1)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer, bruksområde xml_buffer,
      senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
    -> GML_Original
    -> AttributeCopier
GML_Original: Inspector [off]
    TACKATTRS = fme_feature_type
Counter
    CNT_ATTR = _count
    START = 1
    DOMAIN = counter
    SCOPE = Global
    -> TestFilter
    -> GeometryExtractor
GeometryExtractor
    REMOVE_GEOMETRY = No
    ATTR = _geometry
    OGC_WKT_PRECISION_DISPLAY = Shortened 64-bit
    OGCVERSION = 1.1
    KIND_LONG = OGC Well Known Text
    -> FeatureMerger_2 [input 1]
Note: Kobler til assoiserte
FeatureMerger_2
    JOIN_KEYS = @Value(_count) @Value(_mainCount) AUTO
    SUPPLIER_PREFIX = Association
    ATTR_ACCUM_MODE = Prefix Supplier
    IGNORE_NULLS = Yes
    SUPPLIERS_FIRST = No
    MERGE_TYPE = Attributes Only
    PROCESS_DUPS = No
    NOT_MERGED -> AttributeRemover_2
    MERGED -> AttributeRemover_2
AttributeRemover_2
    LIST_ATTRS = _headers{} _headers{}.name _headers{}.value
    REMOVE_ATTRS = _inside_z,_response_body,_inside_y,_http_status_code,_inside_x,_schemamapper_row_ids
    -> NullAttributeMapper_2
    -> FeatureMerger [input 1]
NullAttributeMapper_2
    NULL_TREATMENT = Missing
    ATTRCHOICE = All Attributes
    SOURCE_ATTR_VAL = Null Empty "Missing (Selected Attributes Only)"
    OTHER_VALUE = 0
    -> AttributeExploder
FeatureMerger
    JOIN_KEYS = @Value(_count) @Value(_count) AUTO
    ATTR_ACCUM_MODE = Merge Supplier
    IGNORE_NULLS = No
    ATTR_CONFLICT_RES = Use Requestor
    SUPPLIERS_FIRST = No
    MERGE_TYPE = Attributes Only
    PROCESS_DUPS = No
    MERGED -> PythonCaller
    NOT_MERGED -> PythonCaller
text_line (writer TEXTLINE_1)
    attributes: text_line_data buffer
Reprojector [off]
    INTERPOLATION_TYPE_NAME = Nearest Neighbor
    RASTER_CELL_SIZE = Preserve Cells
    SOURCE = Read from feature
    DEST = EPSG:25833
    REPROJECTED -> StikkrenneKulvert_79 (writer GDMMAPPERSOSI_1) [off]
StikkrenneKulvert_79 (writer GDMMAPPERSOSI_1)
    attributes: DATAFANGSTDATO char(200), KVALITET.MÅLEMETODE char(200), KVALITET.NØYAKTIGHET char(200), KVALITET.SYNBARHET char(200), KVALITET.H-MÅLEMETODE char(200), KVALITET.H-NØYAKTIGHET char(200), KVALITET.MAX-AVVIK char(200), HREF char(200), vegident.Vegident.vegkategori buffer, identifikasjon.Identifikasjon.lokalId buffer, identifikasjon.Identifikasjon.navnerom buffer, identifikasjon.Identifikasjon.versjonId buffer, oppdateringsdato buffer, vegident.Vegident.vegstatus buffer, vegident.Vegident.vegnummer int32, sideposisjon buffer, tverrsnittsform buffer, høydeInnvendig int32, breddeInnvendig int32, typeInnløp buffer, harInnløpsrist buffer, typeUtløp buffer, eier buffer, materialtype buffer, bruksområde buffer, senterlinje buffer, navn buffer, byggeår int32, spesielleProblem buffer, tiltakOppstrøms buffer,
      tilknyttetLukkaDren buffer, gjennomløpForElvBekk buffer, dokumentasjon.NVDB_Dokumentasjon.type buffer, dokumentasjon.NVDB_Dokumentasjon.filnavn buffer, dokumentasjon.NVDB_Dokumentasjon.tekst buffer, dokumentasjon.NVDB_Dokumentasjon.merknad buffer, kommentar.NVDB_Kommentar.beskrivelse buffer, tilstandSkade.TilstandSkadePunkt.tilstand buffer, tilstandSkade.TilstandSkadePunkt.skadetype buffer, tilstandSkade.TilstandSkadePunkt.datoKontrollert buffer, tilstandSkade.TilstandSkadePunkt.tiltak buffer, tilstandSkade.TilstandSkadePunkt.tiltakNår buffer, tilstandSkade.TilstandSkadePunkt.tilleggsinformasjon buffer, tilrettelagtFiskevandring buffer, prosesshistorie buffer, kommunenummer buffer, produktinformasjon buffer, prefabrikkert buffer, retning buffer, vinkel buffer, diameterInnvendig int32, lengde real64, helningFall real64, overfyllingInnløp real64, overfyllingUtløp real64, tykkelseOverfylling real64, posisjon buffer, driftsmerking buffer, fundamentering buffer, varmekabler buffer,
      vedlikeholdsansvarlig buffer, område buffer, _closest_candidate_y char(200), _list{}.vegident.Vegident.vegkategori char(200), _list{}.vk char(200), _list{}.identifikasjon.Identifikasjon.lokalId char(200), _list{}.identifikasjon.Identifikasjon.navnerom char(200), _list{}.identifikasjon.Identifikasjon.versjonId char(200), _list{}.endringsflagg.Endringsflagg.typeEndring char(200), _list{}.endringsflagg.Endringsflagg.tidspunktEndring char(200), _list{}.datafangstdato char(200), _list{}.oppdateringsdato char(200), _list{}.kvalitet.Posisjonskvalitet.målemetode char(200), _list{}.kvalitet.Posisjonskvalitet.nøyaktighet char(200), _list{}.kvalitet.Posisjonskvalitet.synbarhet char(200), _list{}.kvalitet.Posisjonskvalitet.målemetodeHøyde char(200), _list{}.kvalitet.Posisjonskvalitet.nøyaktighetHøyde char(200), _list{}.kvalitet.Posisjonskvalitet.maksimaltAvvik char(200), _list{}.høydereferanse char(200), _list{}.vegident.Vegident.vegstatus char(200), _list{}.vegident.Vegident.vegnummer char(200), _list{}.vegparsell.Vegparsell.hovedParsell char(200), _list{}.vegparsell.Vegparsell.veglenkeMeterFra char(200), _list{}.vegparsell.Vegparsell.veglenkeMeterTil char(200), _list{}.sideposisjon char(200), _list{}.tverrsnittsform char(200), _list{}.høydeInnvendig char(200), _list{}.breddeInnvendig char(200), _list{}.typeInnløp char(200), _list{}.harInnløpsrist char(200),
      _list{}.typeUtløp char(200), _list{}.eier char(200), _list{}.materialtype char(200), _list{}.bruksområde char(200), _list{}.senterlinje char(200), _list{}.navn char(200), _list{}.byggeår char(200), _list{}.spesielleProblem char(200), _list{}.antallTininger char(200), _list{}.tiltakOppstrøms char(200), _list{}.tilknyttetLukkaDren char(200), _list{}.gjennomløpForElvBekk char(200), _list{}.dokumentasjon.NVDB_Dokumentasjon.type char(200), _list{}.dokumentasjon.NVDB_Dokumentasjon.filnavn char(200), _list{}.dokumentasjon.NVDB_Dokumentasjon.tekst char(200), _list{}.dokumentasjon.NVDB_Dokumentasjon.merknad char(200), _list{}.kommentar.NVDB_Kommentar.beskrivelse char(200), _list{}.tilstandSkade.TilstandSkadePunkt.tilstand char(200), _list{}.tilstandSkade.TilstandSkadePunkt.skadetype char(200), _list{}.tilstandSkade.TilstandSkadePunkt.datoKontrollert char(200), _list{}.tilstandSkade.TilstandSkadePunkt.tiltak char(200), _list{}.tilstandSkade.TilstandSkadePunkt.tiltakNår char(200), _list{}.tilstandSkade.TilstandSkadePunkt.tilleggsinformasjon char(200), _list{}.tilrettelagtFiskevandring char(200), _list{}.fme_feature_type char(200), _list{}.gml_parent_id char(200), _list{}.gml_parent_property char(200), _list{}.gml_id char(200), _list{}.fme_basename char(200), _list{}.Vegreferanse.vegkategori char(200),
      _list{}.prosesshistorie char(200), _list{}.kommunenummer char(200), _list{}.vegreferanse{}.Vegreferanse.vegkategori char(200), _list{}.vegreferanse{}.Vegreferanse.vegstatus char(200), _list{}.vegreferanse{}.Vegreferanse.vegnummer char(200), _list{}.vegreferanse{}.Vegreferanse.hovedParsell char(200), _list{}.vegreferanse{}.Vegreferanse.veglenkeMeterFra char(200), _list{}.vegreferanse{}.Vegreferanse.veglenkeMeterTil char(200), _list{}.produktinformasjon char(200), _list{}.prefabrikkert char(200), _list{}.retning char(200), _list{}.vinkel char(200), _list{}.diameterInnvendig char(200), _list{}.lengde char(200), _list{}.helningFall char(200), _list{}.overfyllingInnløp char(200), _list{}.overfyllingUtløp char(200), _list{}.tykkelseOverfylling char(200), _list{}.posisjon char(200), _list{}.driftsmerking char(200), _list{}.fundamentering char(200), _list{}.varmekabler char(200), _list{}.vedlikeholdsansvarlig char(200), _list{}.område char(200), _list{}.assosiertTilstandSkadeFUPunkt{}.nilReason char(200), _list{}.assosiertTilstandSkadeFUPunkt{}.gml_remoteSchema char(200), _list{}.assosiertTilstandSkadeFUPunkt{}.xlink_href char(200), _list{}.assosiertTilstandSkadeFUPunkt{}.owns char(200), _list{}.assosiertTilstandsgradStikkrenneKulvertTe{}.nilReason char(200), _list{}.assosiertTilstandsgradStikkrenneKulvertTe{}.gml_remoteSchema char(200),
      _list{}.assosiertTilstandsgradStikkrenneKulvertTe{}.xlink_href char(200), _list{}.assosiertTilstandsgradStikkrenneKulvertTe{}.owns char(200), _list{}.assosiertTilstandSkadePunkt{}.nilReason char(200), _list{}.assosiertTilstandSkadePunkt{}.gml_remoteSchema char(200), _list{}.assosiertTilstandSkadePunkt{}.xlink_href char(200), _list{}.assosiertTilstandSkadePunkt{}.owns char(200), _list{}.assosiertSystemobjekt{}.nilReason char(200), _list{}.assosiertSystemobjekt{}.gml_remoteSchema char(200), _list{}.assosiertSystemobjekt{}.xlink_href char(200), _list{}.assosiertSystemobjekt{}.owns char(200), _list{}.assosiertNVDB_Kum{}.nilReason char(200), _list{}.assosiertNVDB_Kum{}.gml_remoteSchema char(200), _list{}.assosiertNVDB_Kum{}.xlink_href char(200), _list{}.assosiertNVDB_Kum{}.owns char(200), _list{}.assosiertNVDB_Kommentar{}.nilReason char(200), _list{}.assosiertNVDB_Kommentar{}.gml_remoteSchema char(200), _list{}.assosiertNVDB_Kommentar{}.xlink_href char(200), _list{}.assosiertNVDB_Kommentar{}.owns char(200), _list{}.assosiertNVDB_Dokumentasjon{}.nilReason char(200), _list{}.assosiertNVDB_Dokumentasjon{}.gml_remoteSchema char(200), _list{}.assosiertNVDB_Dokumentasjon{}.xlink_href char(200), _list{}.assosiertNVDB_Dokumentasjon{}.owns char(200), _list{}.Vegreferanse.vegstatus char(200), _list{}.Vegreferanse.vegnummer char(200), _list{}.Vegreferanse.hovedParsell char(200), _list{}.Vegreferanse.veglenkeMeterFra char(200), _list{}.Vegreferanse.veglenkeMeterTil char(200), _list{}._distance char(200), _list{}._angle char(200), _list{}._candidate_angle char(200),
      _list{}._candidate_label_angle char(200), _list{}._closest_candidate_x char(200), _list{}._closest_candidate_y char(200), _list{}._closest_base_x char(200), _list{}._closest_base_y char(200), _list{}.distance char(200), _list{}.angle char(200), _list{}.candidate_angle char(200), _list{}.candidate_label_angle char(200), _list{}.closest_candidate_x char(200), _list{}.closest_candidate_y char(200), _list{}.closest_base_x char(200), _list{}.closest_base_y char(200), _list{}._geometry char(200), _list{}._element_index char(200), vk char(200), antallTininger int32, Vegreferanse.vegkategori char(200), vegreferanse{}.Vegreferanse.vegkategori buffer, vegreferanse{}.Vegreferanse.vegstatus buffer, vegreferanse{}.Vegreferanse.vegnummer int32, vegreferanse{}.Vegreferanse.hovedParsell int32, vegreferanse{}.Vegreferanse.veglenkeMeterFra int32, vegreferanse{}.Vegreferanse.veglenkeMeterTil int32, assosiertTilstandSkadeFUPunkt{}.nilReason buffer, assosiertTilstandSkadeFUPunkt{}.gml_remoteSchema buffer, assosiertTilstandSkadeFUPunkt{}.xlink_href buffer, assosiertTilstandSkadeFUPunkt{}.owns logical, assosiertTilstandsgradStikkrenneKulvertTe{}.nilReason buffer, assosiertTilstandsgradStikkrenneKulvertTe{}.gml_remoteSchema buffer,
      assosiertTilstandsgradStikkrenneKulvertTe{}.xlink_href buffer, assosiertTilstandsgradStikkrenneKulvertTe{}.owns logical, assosiertTilstandSkadePunkt{}.nilReason buffer, assosiertTilstandSkadePunkt{}.gml_remoteSchema buffer, assosiertTilstandSkadePunkt{}.xlink_href buffer, assosiertTilstandSkadePunkt{}.owns logical, assosiertSystemobjekt{}.nilReason buffer, assosiertSystemobjekt{}.gml_remoteSchema buffer, assosiertSystemobjekt{}.xlink_href buffer, assosiertSystemobjekt{}.owns logical, assosiertNVDB_Kum{}.nilReason buffer, assosiertNVDB_Kum{}.gml_remoteSchema buffer, assosiertNVDB_Kum{}.xlink_href buffer, assosiertNVDB_Kum{}.owns logical, assosiertNVDB_Kommentar{}.nilReason buffer, assosiertNVDB_Kommentar{}.gml_remoteSchema buffer, assosiertNVDB_Kommentar{}.xlink_href buffer, assosiertNVDB_Kommentar{}.owns logical, assosiertNVDB_Dokumentasjon{}.nilReason buffer, assosiertNVDB_Dokumentasjon{}.gml_remoteSchema buffer, assosiertNVDB_Dokumentasjon{}.xlink_href buffer, assosiertNVDB_Dokumentasjon{}.owns logical, Vegreferanse.vegstatus char(200), Vegreferanse.vegnummer char(200), Vegreferanse.hovedParsell char(200), Vegreferanse.veglenkeMeterFra char(200), Vegreferanse.veglenkeMeterTil char(200), _distance char(200), _angle char(200), _candidate_angle char(200),
      _candidate_label_angle char(200), _closest_candidate_x char(200), _closest_base_x char(200), _closest_base_y char(200), distance char(200), angle char(200), candidate_angle char(200), candidate_label_angle char(200), closest_candidate_x char(200), closest_candidate_y char(200), closest_base_x char(200), closest_base_y char(200), _element_index char(200)

Bookmark: Identifiserer eksisterende i NVDB
Note: NVDB: StikkrenneKulvert [GML]
StikkrenneKulvert (reader GML_2)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, prosesshistorie xml_buffer, høydereferanse xml_buffer, kommunenummer xml_buffer, sideposisjon xml_buffer, vegreferanse{}.Vegreferanse.vegkategori xml_buffer, vegreferanse{}.Vegreferanse.vegstatus xml_buffer, vegreferanse{}.Vegreferanse.vegnummer xml_int64, vegreferanse{}.Vegreferanse.hovedParsell xml_int64, vegreferanse{}.Vegreferanse.veglenkeMeterFra xml_int64, vegreferanse{}.Vegreferanse.veglenkeMeterTil xml_int64, bruksområde xml_buffer, navn xml_buffer, byggeår xml_int64, produktinformasjon xml_buffer, materialtype xml_buffer, prefabrikkert xml_buffer, retning xml_buffer,
      vinkel xml_buffer, tilknyttetLukkaDren xml_buffer, gjennomløpForElvBekk xml_buffer, typeInnløp xml_buffer, typeUtløp xml_buffer, harInnløpsrist xml_buffer, diameterInnvendig xml_int64, breddeInnvendig xml_int64, høydeInnvendig xml_int64, lengde xml_real64, helningFall xml_real64, tverrsnittsform xml_buffer, overfyllingInnløp xml_real64, overfyllingUtløp xml_real64, tykkelseOverfylling xml_real64, posisjon xml_geometry, senterlinje xml_geometry, driftsmerking xml_buffer, fundamentering xml_buffer, varmekabler xml_buffer, antallTininger xml_int64, spesielleProblem xml_buffer, eier xml_buffer, vedlikeholdsansvarlig xml_buffer, område xml_geometry, assosiertTilstandSkadeFUPunkt{}.nilReason xml_buffer, assosiertTilstandSkadeFUPunkt{}.gml_remoteSchema xml_buffer, assosiertTilstandSkadeFUPunkt{}.xlink_href xml_buffer, assosiertTilstandSkadeFUPunkt{}.owns xml_boolean, assosiertTilstandsgradStikkrenneKulvertTe{}.nilReason xml_buffer,
      assosiertTilstandsgradStikkrenneKulvertTe{}.gml_remoteSchema xml_buffer, assosiertTilstandsgradStikkrenneKulvertTe{}.xlink_href xml_buffer, assosiertTilstandsgradStikkrenneKulvertTe{}.owns xml_boolean, assosiertTilstandSkadePunkt{}.nilReason xml_buffer, assosiertTilstandSkadePunkt{}.gml_remoteSchema xml_buffer, assosiertTilstandSkadePunkt{}.xlink_href xml_buffer, assosiertTilstandSkadePunkt{}.owns xml_boolean, assosiertSystemobjekt{}.nilReason xml_buffer, assosiertSystemobjekt{}.gml_remoteSchema xml_buffer, assosiertSystemobjekt{}.xlink_href xml_buffer, assosiertSystemobjekt{}.owns xml_boolean, assosiertNVDB_Kum{}.nilReason xml_buffer, assosiertNVDB_Kum{}.gml_remoteSchema xml_buffer, assosiertNVDB_Kum{}.xlink_href xml_buffer, assosiertNVDB_Kum{}.owns xml_boolean, assosiertNVDB_Kommentar{}.nilReason xml_buffer, assosiertNVDB_Kommentar{}.gml_remoteSchema xml_buffer, assosiertNVDB_Kommentar{}.xlink_href xml_buffer, assosiertNVDB_Kommentar{}.owns xml_boolean, assosiertNVDB_Dokumentasjon{}.nilReason xml_buffer, assosiertNVDB_Dokumentasjon{}.gml_remoteSchema xml_buffer, assosiertNVDB_Dokumentasjon{}.xlink_href xml_buffer, assosiertNVDB_Dokumentasjon{}.owns xml_boolean
    -> Reprojector_3
    -> NVDB_StikkrenneKulvert
Reprojector_3
    INTERPOLATION_TYPE_NAME = Nearest Neighbor
    RASTER_CELL_SIZE = Preserve Cells
    SOURCE = Read from feature
    DEST = EPSG:25832
    REPROJECTED -> AttributeCopier_2
AttributeCopier_2
    ATTR_TABLE = COPY @Value(vegreferanse{0}.Vegreferanse.vegkategori) > vk
    -> ListIndexer
ListIndexer
    LIST_ATTR = vegreferanse{}
    INDEX = 0
    -> AttributeCopier_3
AttributeCopier_3
    ATTR_TABLE = COPY Vegreferanse.vegkategori > vk
    -> NeighborFinder [input 2]
NVDB_StikkrenneKulvert: Inspector [off]
AttributeCopier
    ATTR_TABLE = COPY vegident.Vegident.vegkategori > vk
    -> NeighborFinder [input 1]
Note: Finner nærliggende NVDB-objekter (inntil 3 stk)
NeighborFinder
    ATTR_ACCUM_MODE = Merge Candidate
    INSERT_VERTEX = No
    TREAT_POLYGON_AS = Lines
    MODE = Bases and Candidates
    K = 3
    CANDIDATES_FIRST = No
    ATTR_CONFLICT_RES = Use Base
    GROUP_BY = vk
    CLOSE_LIST_NAME = _ccList
    MAX = 10
    MATCHED -> GeometryExtractor_2
    MATCHED -> AttributeRemover_3
    UNMATCHED_BASE -> AttributeRemover_3
GeometryExtractor_2
    PREFER_POLYGON_OVER_SURFACE = No
    REMOVE_GEOMETRY = No
    ELLIPSOID_NAME = WGS84
    ATTR = _geometry
    PRECISION = 0
    LEVELS_ATTR = _levels
    OGC_WKT_PRECISION_DISPLAY = Shortened 64-bit
    OMIT_NAMESPACES_DISPLAY = No
    OGEOSMS_URL_PREFIX = http://maps.google.com/?q=
    OGCVERSION = 1.1
    KIND_LONG = FME Binary
    LETTERING = WGS84
    GEOHASH_PRECISION_DISPLAY = ~9.3 mm (12 characters)
    -> ListDuplicateRemover
ListDuplicateRemover
    SRC_LIST = _ccList{}.identifikasjon.Identifikasjon.lokalId
    -> ListExploder
ListExploder
    ATTR_ACCUM_MODE = Merge Incoming List
    INDEX_ATTR = _element_index
    ATTR_CONFLICT_RES = Use Original
    LIST_ATTR = _ccList{}
    ELEMENTS -> ListBuilder_2
ListBuilder_2
    GRP_BY = identifikasjon.Identifikasjon.versjonId identifikasjon.Identifikasjon.lokalId identifikasjon.Identifikasjon.navnerom
    LIST_NAME = _list
    -> ListSorter
ListSorter
    SRC_LIST = _list{}.distance
    ORDER = Ascending
    TYPE = Numeric
    -> ListIndexer_2
Note: Nærmeste pr NVDB-ID
ListIndexer_2
    LIST_ATTR = _list{}
    INDEX = 0
    -> GeometryReplacer
GeometryReplacer
    SOURCE = @Value(_geometry)
    OGC_WKT_PRECISION_DISPLAY = 64-bit
    REMOVE_ATTRIBUTE = Yes
    KIND_LONG = FME Binary
    -> AttributeCreator_3
Note: typeEndring = E
AttributeCreator_3
    ATTR_TABLE = SET_TO endringsflagg.Endringsflagg.typeEndring = E
    -> Stikkrenne (writer GML_3)
    -> FeatureMerger_3 [input 2]
Note: Stikkrenne: KoblingNVDB [GML]
Stikkrenne (writer GML_3)
    attributes: identifikasjon.Identifikasjon.lokalId xml_buffer, identifikasjon.Identifikasjon.navnerom xml_buffer, identifikasjon.Identifikasjon.versjonId xml_buffer, endringsflagg.Endringsflagg.typeEndring xml_buffer, endringsflagg.Endringsflagg.tidspunktEndring xml_date, datafangstdato xml_date, oppdateringsdato xml_date, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, høydereferanse xml_buffer, vegident.Vegident.vegkategori xml_buffer, vegident.Vegident.vegstatus xml_buffer, vegident.Vegident.vegnummer xml_int64, vegparsell.Vegparsell.hovedParsell xml_int64, vegparsell.Vegparsell.veglenkeMeterFra xml_int64, vegparsell.Vegparsell.veglenkeMeterTil xml_int64, sideposisjon xml_buffer, tverrsnittsform xml_buffer, høydeInnvendig xml_int64, breddeInnvendig xml_int64, typeInnløp xml_buffer, harInnløpsrist xml_buffer, typeUtløp xml_buffer, eier xml_buffer, materialtype xml_buffer, bruksområde xml_buffer,
      senterlinje xml_geometry, navn xml_buffer, byggeår xml_int64, spesielleProblem xml_buffer, antallTininger xml_int64, tiltakOppstrøms xml_buffer, tilknyttetLukkaDren xml_buffer, gjennomløpForElvBekk xml_buffer, dokumentasjon.NVDB_Dokumentasjon.type xml_buffer, dokumentasjon.NVDB_Dokumentasjon.filnavn xml_buffer, dokumentasjon.NVDB_Dokumentasjon.tekst xml_buffer, dokumentasjon.NVDB_Dokumentasjon.merknad xml_buffer, kommentar.NVDB_Kommentar.beskrivelse xml_buffer, tilstandSkade.TilstandSkadePunkt.tilstand xml_buffer, tilstandSkade.TilstandSkadePunkt.skadetype xml_buffer, tilstandSkade.TilstandSkadePunkt.datoKontrollert xml_date, tilstandSkade.TilstandSkadePunkt.tiltak xml_buffer, tilstandSkade.TilstandSkadePunkt.tiltakNår xml_buffer, tilstandSkade.TilstandSkadePunkt.tilleggsinformasjon xml_buffer, tilrettelagtFiskevandring xml_buffer
AttributeRemover_3
    LIST_ATTRS = _ccList{} assosiertNVDB_Dokumentasjon{} assosiertNVDB_Kommentar{} assosiertNVDB_Kum{} assosiertSystemobjekt{} assosiertTilstandSkadeFUPunkt{} assosiertTilstandSkadePunkt{} assosiertTilstandsgradStikkrenneKulvertTe{} vegreferanse{}
    REMOVE_ATTRS = Vegreferanse.vegkategori,_angle,antallTininger,_distance,_candidate_label_angle,vegparsell.Vegparsell.veglenkeMeterTil,vk,Vegreferanse.vegnummer,Vegreferanse.vegstatus,_closest_base_y,_closest_candidate_x,vegparsell.Vegparsell.veglenkeMeterFra,vegparsell.Vegparsell.hovedParsell,Vegreferanse.hovedParsell,Vegreferanse.veglenkeMeterTil,_candidate_angle,Vegreferanse.veglenkeMeterFra,_closest_base_x
    -> FeatureMerger_3 [input 1]
FeatureMerger_3
    JOIN_KEYS = @Value(gml_id) @Value(gml_id) AUTO
    ATTR_ACCUM_MODE = Merge Supplier
    IGNORE_NULLS = No
    ATTR_CONFLICT_RES = Use Supplier
    SUPPLIERS_FIRST = No
    MERGE_TYPE = Attributes Only
    PROCESS_DUPS = No
    NOT_MERGED -> SchemaMapper
    MERGED -> SchemaMapper

Bookmark: Mapping til Datakatalog-IDer
Note: Mapper objekttypenavn til VOT-ID, vha mappingtabell ftMapping
SchemaMapper
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    IDXSOURCECOL = name
    CSV__SCHEMA_WITH_COL_NAMES = ftid,number,3,0,name,char,50,
    CSV__ALLOW_SPACES_IN_COLUMN_NAMES = yes
    CSV__STRIP_QUOTES = yes
    CSV__FIELD_NAMES_AFTER_HEADER = no
    IDXSOURCEATTR = fme_feature_type
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_FIELD_NAMES = YES
    CSV__DUPLICATE_DELIMS = no
    DATASET = C:\DATA\NIFS\Mapping\NIFS_ftMapping.csv
    CSV__IN_SEPARATOR = ;
    CSV__SCHEMA = number,3,0,char,50,
    FORMAT = CSV
    IDXDESTCOL = ftid
    CSV_SCAN_MAX_FEATURES = 1000
    ROW_ID_ATTR = _schemamapper_row_ids
    CSV__SKIP_FOOTER = 0
    CSV__GROUP_BY_DATASET = no
    IDXDESTATTR = fme_feature_type
    MAPPED -> AttributeExposer
AttributeExposer
    ATTR_LIST = fme_feature_type
    -> SchemaMapper_2
Note: Mapper egenskapsnavn til ET-ID, vha mappingtabell ptMapping
SchemaMapper_2
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    IDXSOURCECOL = ""
    CSV__SCHEMA_WITH_COL_NAMES = ft_attr,char,17,,ftid,number,3,0,ptid,number,6,0,name,char,21,
    CSV__ALLOW_SPACES_IN_COLUMN_NAMES = yes
    CSV__STRIP_QUOTES = yes
    CSV__FIELD_NAMES_AFTER_HEADER = no
    IDXSOURCEATTR = fme_feature_type
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_FIELD_NAMES = YES
    CSV__DUPLICATE_DELIMS = no
    MATCH_ATTRS = ft_attr ftid
    DATASET = C:\DATA\NIFS\Mapping\NIFS_ptMapping.csv
    CSV__IN_SEPARATOR = ;
    CSV__SCHEMA = char,17,,number,3,0,number,6,0,char,21,
    FORMAT = CSV
    IDXDESTCOL = ""
    CSV_SCAN_MAX_FEATURES = 1000
    ROW_ID_ATTR = _schemamapper_row_ids
    CSV__SKIP_FOOTER = 0
    CSV__GROUP_BY_DATASET = no
    MAP_ATTRS = name ptid $(FME_ASC_16)
    IDXDESTATTR = fme_feature_type
    MAPPED -> SchemaMapper_3
    MAPPED -> Reprojector_2
Note: Mapper egenskapsverdier til TV-ID, vha mappingtabell enMapping
SchemaMapper_3 [off]
    TABLE = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name\"%%\"Filter\"%\"STRING_ENCODED _FILTER_REGEX \"%%\"Invert Filter\"%\"CHECKBOX _FILTER_UNMATCHED yes%no\"%no"
    IDXSOURCECOL = ""
    CSV__SCHEMA_WITH_COL_NAMES = ptid,number,6,0,enid,number,6,0,name,char,31,
    CSV__ALLOW_SPACES_IN_COLUMN_NAMES = yes
    CSV__STRIP_QUOTES = yes
    CSV__FIELD_NAMES_AFTER_HEADER = no
    IDXSOURCEATTR = fme_feature_type
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_FIELD_NAMES = YES
    CSV__DUPLICATE_DELIMS = no
    MATCH_ATTRS = ptid name
    DATASET = C:\DATA\NIFS\Mapping\79_enMapping.csv
    CSV__IN_SEPARATOR = ;
    CSV__SCHEMA = number,6,0,number,6,0,char,31,
    FORMAT = CSV
    IDXDESTCOL = ""
    CSV_SCAN_MAX_FEATURES = 1000
    ROW_ID_ATTR = _schemamapper_row_ids
    CSV__SKIP_FOOTER = 0
    CSV__GROUP_BY_DATASET = no
    MAP_ATTRS = """""" ptid enid
    IDXDESTATTR = fme_feature_type
    MAPPED -> SchemaMapper_4 [off]

Bookmark: Posisjon på referanselenke (senterpunkt for linja)
Reprojector_2
    INTERPOLATION_TYPE_NAME = Nearest Neighbor
    RASTER_CELL_SIZE = Preserve Cells
    SOURCE = Read from feature
    DEST = EPSG:25833
    REPROJECTED -> CenterPointExtractor
CenterPointExtractor
    MODE = Center
    CENTZ = _inside_z
    CENTX = _inside_x
    CENTY = _inside_y
    -> AttributeCreator
AttributeCreator
    ATTR_LIST = httpReq,http://multirit.triona.se/visveginfo/RoadInfoService/GetRoadReferenceForLocation?easting=@Value(_inside_x)&northing=@Value(_inside_y)&coordinateSystem=UTM33&bufferMeters=10searchRoadCategories=@Value(vegident.Vegident.vegkategori)
    -> HTTPCaller
Note: HTTPCaller [HTTPCaller:1] / Target URL: @Value(httpReq) / HTTP Method: GET / Additional URL Parameters: <not set> / Custom Headers: <not set> / Target Attribute: _response_body / Target Attribute Encoding: auto-detect / Version: 1 / Last Parameter Edit: Build 16085
HTTPCaller
    FOLLOW_REDIRECTS = Yes
    RESPONSE_HEADER_LIST_ATTR = _headers
    TARGET_ATTR = _response_body
    CONNECTION_TIMEOUT_LENGTH = 60
    TARGET_URL = @Value(httpReq)
    TRANSFER_TIMEOUT_LENGTH = 90
    TARGET_ATTR_ENCODING = auto-detect
    STATUS_CODE_ATTR = _http_status_code
    ERROR_ATTR = _error
    HTTP_METHOD = GET
    USE_COOKIES = No
    VERIFY_SSL_CERTIFICATES = Yes
    SAVE_FILE = Attribute
    -> XMLFlattener
XMLFlattener
    XML_SOURCE_TYPE = Attribute with XML document
    EMBEDDED_EXPRESSIONS = ReflinkOID Measure
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    FEATURE_TYPES_FORMAT_NAME = XML
    NEW_ATTRIBUTES = ReflinkOID Measure
    ATTRIBUTE_XML = _response_body
    -> Counter

Bookmark: Spesialhåndtering av assosiert tilstand/skade for disse dataene, ikke permanent løsning
TestFilter
    TEST_LIST:
      BOOL_OP,OR,COMPOSITE_TEST,<Unused>,TEST_CLAUSE,"TEST @Value(tilstandSkade.TilstandSkadePunkt.datoKontrollert) ATTRIBUTE_HAS_VALUE """"
      TEST @Value(tilstandSkade.TilstandSkadePunkt.skadetype) ATTRIBUTE_HAS_VALUE """"
      TEST @Value(tilstandSkade.TilstandSkadePunkt.tilleggsinformasjon) ATTRIBUTE_HAS_VALUE """"
      TEST @Value(tilstandSkade.TilstandSkadePunkt.tilstand) ATTRIBUTE_HAS_VALUE """"
      TEST @Value(tilstandSkade.TilstandSkadePunkt.tiltak) ATTRIBUTE_HAS_VALUE """"
      TEST @Value(tilstandSkade.TilstandSkadePunkt.tiltakNår) ATTRIBUTE_HAS_VALUE """"",TilstandSkade
    DEFAULT_VALUE = <UNFILTERED>
    TilstandSkade -> AttributeRenamer_2
AttributeRenamer_2
    ATTR_TABLE = RENAME_SET_DEFAULT _count > _mainCount
    -> Counter_2
Counter_2
    CNT_ATTR = _count
    START = 1
    DOMAIN = counter
    SCOPE = Global
    -> AttributeKeeper_3
AttributeKeeper_3
    KEEP_ATTRS = tilstandSkade.TilstandSkadePunkt.tiltak,_count,tilstandSkade.TilstandSkadePunkt.tiltakNår,ReflinkOID,fme_basename,tilstandSkade.TilstandSkadePunkt.tilleggsinformasjon,tilstandSkade.TilstandSkadePunkt.tilstand,_mainCount,tilstandSkade.TilstandSkadePunkt.datoKontrollert,tilstandSkade.TilstandSkadePunkt.skadetype,Measure,fme_feature_type
    -> AttributeRenamer_3
AttributeRenamer_3
    ATTR_TABLE:
      RENAME_SET_DEFAULT tilstandSkade.TilstandSkadePunkt.tilstand > 7596
      RENAME_SET_DEFAULT tilstandSkade.TilstandSkadePunkt.skadetype > 7590
      RENAME_SET_DEFAULT tilstandSkade.TilstandSkadePunkt.datoKontrollert > 8777
      RENAME_SET_DEFAULT tilstandSkade.TilstandSkadePunkt.tiltak > 7594
      RENAME_SET_DEFAULT tilstandSkade.TilstandSkadePunkt.tiltakNår > 7595
      RENAME_SET_DEFAULT tilstandSkade.TilstandSkadePunkt.tilleggsinformasjon > 7859
    -> AttributeCreator_2
AttributeCreator_2
    ATTR_TABLE = SET_TO fme_feature_type = 761
    -> GeometryRemover
GeometryRemover
    -> AttributeRemover_2
    -> AttributeKeeper_4
AttributeKeeper_4
    KEEP_ATTRS = _count,_mainCount
    -> FeatureMerger_2 [input 2]

Bookmark: XML for hver egenskap
AttributeExploder
    ATTR_VALUE_LABEL = _attr_value
    KEEP_ATTRIBUTES = Yes
    KEEP_GEOMETRY = No
    EXPLODING_TYPE = Features
    ATTR_NAME_LABEL = _attr_name
    -> AttributeKeeper
AttributeKeeper
    KEEP_ATTRS = _count,_attr_name,endringsflagg.Endringsflagg.typeEndring,_attr_value
    -> AttributeValidator
AttributeValidator
    TABLE = _attr_name|TYPE|NUM
    PASSED -> TestFilter_3
TestFilter_3
    TEST_LIST = BOOL_OP,OR,COMPOSITE_TEST,<Unused>,TEST_CLAUSE,"TEST @Value(endringsflagg.Endringsflagg.typeEndring) = E",Endring
    DEFAULT_VALUE = Ny
    Ny -> XMLTemplater_3
    Endring -> XMLTemplater_6
XMLTemplater_6
    ROOT_QUERY_EXPR:
      <egenskap typeId="{fme:get-attribute("_attr_name")}" operasjon="oppdater">
          <verdi>{fme:get-attribute("_attr_value")}</verdi>
      </egenskap>
    VISIBLE_QUERY_VALIDATE = Yes
    RESULT_ATTRIBUTE = _ptXML
    OUTPUT_XML_HEADER = No
    -> ListBuilder
XMLTemplater_3
    ROOT_QUERY_EXPR:
      <egenskap typeId="{fme:get-attribute("_attr_name")}">
          <verdi>{fme:get-attribute("_attr_value")}</verdi>
      </egenskap>
    VISIBLE_QUERY_VALIDATE = Yes
    RESULT_ATTRIBUTE = _ptXML
    OUTPUT_XML_HEADER = No
    -> ListBuilder
ListBuilder
    GRP_BY = _count
    LIST_NAME = _ptList
    -> FeatureMerger [input 2]

Bookmark: XML for hvert objekt
Note: Kvalitetsstreng
PythonCaller
    PYTHONSOURCE:
      import fmeobjects
      # Template Function interface:

      def setQuality(feature):
          qs=""
          qm = feature.getAttribute('kvalitet.Posisjonskvalitet.målemetode')
          qms=str(qm)
          if qms <> "None":
              qs="målemetode="+qms

          qm = feature.getAttribute('kvalitet.Posisjonskvalitet.nøyaktighet')
          qms=str(qm)
          if qms <> "None":
              qs=qs+"; nøyaktighet="+qms

          qm = feature.getAttribute('kvalitet.Posisjonskvalitet.synbarhet')
          qms=str(qm)
          if qms <> "None":
              qs=qs+"; synbarhet="+qms

          qm = feature.getAttribute('kvalitet.Posisjonskvalitet.målemetodeHøyde')
          qms=str(qm)
          if qms <> "None":
              qs=qs+"; målemetodeHøyde="+qms

          qm = feature.getAttribute('kvalitet.Posisjonskvalitet.nøyaktighetHøyde')
          qms=str(qm)
          if qms <> "None":
              qs=qs+"; nøyaktighetHøyde="+qms

          if qs <> "":
              feature.setAttribute('qualityString', qs+'; ')
    PYTHONSYMBOL = setQuality
    NEW_ATTRIBUTES = qualityString
    -> TestFilter_2
TestFilter_2
    TEST_LIST = BOOL_OP,OR,COMPOSITE_TEST,<Unused>,TEST_CLAUSE,"TEST @Value(endringsflagg.Endringsflagg.typeEndring) = E",Endring
    DEFAULT_VALUE = Ny
    Ny -> XMLTemplater_2
    Endring -> XMLTemplater_5
XMLTemplater_5
    ROOT_QUERY_EXPR:
      <vegObjekt typeId="{fme:get-attribute("fme_feature_type")}" nvdbId="{fme:get-attribute("identifikasjon.Identifikasjon.lokalId")}" versjon="{fme:get-attribute("identifikasjon.Identifikasjon.versjonId")}">
          <egenskaper>
              {fme:get-list-attribute("_ptList{}._ptXML")}
              {if( fme:has-attribute("_geometry")) then
              <egenskap typeId="$(geomProp_2)" operasjon="oppdater">
                  <verdi>{fme:get-attribute("qualityString")}{fme:get-attribute("_geometry")}</verdi>
              </egenskap>
              else ()}
          </egenskaper>
          {if( fme:has-attribute("Association_mainCount")) then
              <assosiasjoner>
              <assosiasjon typeId="221093" operasjon="oppdater">
                  <tempId>-{fme:get-attribute("Association_count")}</tempId>
              </assosiasjon>
          </assosiasjoner>
          else ()}
          <lokasjon operasjon="oppdater">
              <punkt lenkeId="{fme:get-attribute("ReflinkOID")}" posisjon="{fme:get-attribute("Measure")}"/>
          </lokasjon>
      </vegObjekt>
    VISIBLE_QUERY_VALIDATE = Yes
    RESULT_ATTRIBUTE = _result
    OUTPUT_XML_HEADER = No
    -> StringReplacer_3
XMLTemplater_2
    ROOT_QUERY_EXPR:
      <vegObjekt typeId="{fme:get-attribute("fme_feature_type")}" tempId="-{fme:get-attribute("_count")}">
          <egenskaper>
              {fme:get-list-attribute("_ptList{}._ptXML")}
              {if( fme:has-attribute("_geometry")) then
              <egenskap typeId="$(geomProp_2)">
                  <verdi>{fme:get-attribute("qualityString")}{fme:get-attribute("_geometry")}</verdi>
              </egenskap>
              else ()}
          </egenskaper>
          {if( fme:has-attribute("Association_mainCount")) then
              <assosiasjoner>
              <assosiasjon typeId="221093">
                  <tempId>-{fme:get-attribute("Association_count")}</tempId>
              </assosiasjon>
          </assosiasjoner>
          else ()}
          <lokasjon>
              <punkt lenkeId="{fme:get-attribute("ReflinkOID")}" posisjon="{fme:get-attribute("Measure")}"/>
          </lokasjon>
      </vegObjekt>
    VISIBLE_QUERY_VALIDATE = Yes
    RESULT_ATTRIBUTE = _result
    OUTPUT_XML_HEADER = No
    -> StringReplacer_3
StringReplacer_3
    SRC_ATTRS = _result
    FIND_TEXT = &lt;
    REPLACE_TEXT = <
    CASE = NO
    NO_MATCH = _FME_NO_OP_
    REGEXP = NO
    -> StringReplacer_4
StringReplacer_4
    SRC_ATTRS = _result
    FIND_TEXT = &gt;
    REPLACE_TEXT = >
    CASE = NO
    NO_MATCH = _FME_NO_OP_
    REGEXP = NO
    -> AttributeKeeper_2
AttributeKeeper_2
    KEEP_ATTRS = _result,endringsflagg.Endringsflagg.typeEndring,fme_basename
    -> NullAttributeMapper_3
NullAttributeMapper_3
    NULL_TREATMENT = New Value
    ATTRCHOICE = Selected Attributes
    SOURCE_ATTR_VAL = Null Empty "Missing (Selected Attributes Only)"
    NEW_VALUE = N
    ATTRLIST = endringsflagg.Endringsflagg.typeEndring
    -> Aggregator_2

Bookmark: XML for datasettet
Aggregator_2
    MODE = Geometry - Assemble One Level
    ACCUM_ATTRS_NAME = No
    GROUP_BY = endringsflagg.Endringsflagg.typeEndring fme_basename
    LIST_NAME = _featureList
    ORDERED = No
    AGGREGATE_TYPE = Homogeneous Collection (If Possible)
    SEP = ,
    AGGREGATE -> XMLTemplater_4
Note: transaksjonstyper
XMLTemplater_4
    ROOT_QUERY_EXPR:
      {if( {fme:get-attribute("endringsflagg.Endringsflagg.typeEndring")}="E") then
        <delvisOppdater>
          <vegObjekter>
          {fme:get-list-attribute("_featureList{}._result")}
          </vegObjekter>
        </delvisOppdater>
      else  (
        <registrer>
          <vegObjekter>
          {fme:get-list-attribute("_featureList{}._result")}
          </vegObjekter>
        </registrer>)}
    VISIBLE_QUERY_VALIDATE = Yes
    RESULT_ATTRIBUTE = _result
    OUTPUT_XML_HEADER = No
    -> AttributeKeeper_5
AttributeKeeper_5
    KEEP_ATTRS = _result,fme_basename
    -> StringReplacer_5
StringReplacer_5
    SRC_ATTRS = _result
    FIND_TEXT = &lt;
    REPLACE_TEXT = <
    CASE = NO
    NO_MATCH = _FME_NO_OP_
    REGEXP = NO
    -> StringReplacer_6
StringReplacer_6
    SRC_ATTRS = _result
    FIND_TEXT = &gt;
    REPLACE_TEXT = >
    CASE = NO
    NO_MATCH = _FME_NO_OP_
    REGEXP = NO
    -> Aggregator
Aggregator
    MODE = Geometry - Assemble One Level
    ACCUM_ATTRS_NAME = No
    GROUP_BY = fme_basename
    LIST_NAME = _featureList
    ORDERED = No
    AGGREGATE_TYPE = Homogeneous Collection (If Possible)
    SEP = ,
    AGGREGATE -> TimeStamper
TimeStamper
    TIME_ATTR = _timestamp
    FMT = ^Y-^m-^d
    -> XMLTemplater
XMLTemplater
    ROOT_QUERY_EXPR:
      <endringssett xmlns="http://nvdb.vegvesen.no/apiskriv/domain/v2" effektDato="{fme:get-attribute("_timestamp")}" datakatalogversjon="$(version_2)">
      {fme:get-list-attribute("_featureList{}._result")}
      </endringssett>
    VISIBLE_QUERY_VALIDATE = Yes
    RESULT_ATTRIBUTE = _result
    OUTPUT_XML_HEADER = Yes
    -> StringReplacer
StringReplacer
    SRC_ATTRS = _result
    FIND_TEXT = &lt;
    REPLACE_TEXT = <
    CASE = NO
    NO_MATCH = _FME_NO_OP_
    REGEXP = NO
    -> StringReplacer_2
StringReplacer_2
    SRC_ATTRS = _result
    FIND_TEXT = &gt;
    REPLACE_TEXT = >
    CASE = NO
    NO_MATCH = _FME_NO_OP_
    REGEXP = NO
    -> XMLFormatter_2
XMLFormatter_2
    XML_INPUT_TYPE = Attribute Specifying XML Text
    XML_OUTPUT_TYPE = Attribute
    XML_OUTPUT_ATTR = _xml_output
    XML_ATTR_TEXT = _result
    SCHEMALOC_CLEANUP = No
    OUTPUT_ENCODING = utf-8
    REMOVE_EMPTY_ELEMENT = Yes
    COLLAPSE_EMPTY_ELEMENT = No
    REPLACE_TABS_WITH_SPACES = no
    NAMESPACE_CLEANUP = No
    FORMATTING_CHOICE = Pretty-Print XML
    LIST_NAME = _xml_error
    WHITESPACE_HANDLING = Preserve all whitespace
    REMOVE_ALL_COMMENT = No
    INDENT_SIZE = 1
    TEXT_INDENT = no
    PASSED -> text_line (writer TEXTLINE_1)

Bookmark: Mapping til SOSINVDB_navn
Note: Mapper objekttypenavn til SOSINVDB_navn vha Accessbasen
SchemaMapper_4 [off]
    IDXSOURCECOL = ID_VOBJ_TYPE
    ROW_ID_ATTR = _schemamapper_row_ids
    FORMAT = MDB_ADO
    DATASET = C:\DATA\Standardisering\NVDB\NVDB Datakatalogen\Datakatalog_204_733_20151007_dakat.mdb
    IDXDESTATTR = fme_feature_type
    MDB_ADO_QUERY_FEATURE_TYPES_FOR_MERGE_FILTERS = Yes
    IDXDESTCOL = SOSINVDB_navn
    TABLE = VEGOB_TYPE
    IDXSOURCEATTR = fme_feature_type
    MAPPED -> SchemaMapper_5 [off]
Note: Mapper egenskapsnavn til SOSINVDB_navn vha Accessbasen
SchemaMapper_5 [off]
    IDXSOURCECOL = ""
    ROW_ID_ATTR = _schemamapper_row_ids
    FORMAT = MDB_ADO
    DATASET = C:\DATA\Standardisering\NVDB\NVDB Datakatalogen\Datakatalog_204_733_20151007_dakat.mdb
    IDXDESTATTR = fme_feature_type
    MDB_ADO_QUERY_FEATURE_TYPES_FOR_MERGE_FILTERS = Yes
    IDXDESTCOL = ""
    TABLE = EGENSKAPSTYPE
    MAP_ATTRS = ID_EGENSKAPSTYPE SOSINVDB_navn $(FME_ASC_16)
    IDXSOURCEATTR = fme_feature_type
    MAPPED -> NullAttributeMapper [off]
NullAttributeMapper [off]
    NULL_TREATMENT = Missing
    ATTRCHOICE = All Attributes
    SOURCE_ATTR_VAL = Null Empty "Missing (Selected Attributes Only)"
    -> DateFormatter [off]

Bookmark: Navn på generelle SOSI-egenskaper
DateFormatter [off]
    FMT = FME Date (%Y%m%d)
    DATE_ATTR = datafangstdato,endringsflagg.Endringsflagg.tidspunktEndring
    SRCFMT = Unknown - Automatic Detection
    INVALID_DATE_VALUE = _FME_NO_OP_
    -> AttributeRenamer [off]
AttributeRenamer [off]
    ATTR_TABLE:
      RENAME_SET_DEFAULT datafangstdato > DATAFANGSTDATO
      RENAME_SET_DEFAULT kvalitet.Posisjonskvalitet.målemetode > KVALITET.MÅLEMETODE
      RENAME_SET_DEFAULT kvalitet.Posisjonskvalitet.nøyaktighet > KVALITET.NØYAKTIGHET
      RENAME_SET_DEFAULT kvalitet.Posisjonskvalitet.synbarhet > KVALITET.SYNBARHET
      RENAME_SET_DEFAULT kvalitet.Posisjonskvalitet.målemetodeHøyde > KVALITET.H-MÅLEMETODE
      RENAME_SET_DEFAULT kvalitet.Posisjonskvalitet.nøyaktighetHøyde > KVALITET.H-NØYAKTIGHET
      RENAME_SET_DEFAULT kvalitet.Posisjonskvalitet.maksimaltAvvik > KVALITET.MAX-AVVIK
      RENAME_SET_DEFAULT høydereferanse > HREF
    -> AttributeRemover [off]
AttributeRemover [off]
    REMOVE_ATTRS = gml_parent_id,gml_parent_property,vegparsell.Vegparsell.veglenkeMeterTil,_schemamapper_row_ids,endringsflagg.Endringsflagg.tidspunktEndring,gml_id,vegparsell.Vegparsell.hovedParsell,endringsflagg.Endringsflagg.typeEndring,vegparsell.Vegparsell.veglenkeMeterFra
    -> Reprojector [off]
    -> StikkrenneKulvert_79 (writer GDMMAPPERSOSI_1) [off]
