FME workspace Vegnett_TNE2GML (backup).fmw

Parameters:
- knr = 519   # Kommunenummer
- detaljNivå = Kjørefelt   # Detaljnivå
- DestDataset_GML = C:\DATA\Standardisering\NVDBGML\GML\Vegnettstest.gml   # Destination Geography Markup Language (GML) File

Writers:
- GML_1: GML to $(DestDataset_GML)

Creator_2
    NUM = 1
    GEOMTYPE = Geometry Object
    CREATED -> StringConcatenator_6
StringConcatenator_6
    VAL_ATTR = _kommunewhere
    PARM_LINE = KOMM=$(knr)
    -> FeatureReader
FeatureReader
    GEODATABASE_FILE_TRANSLATE_SPATIAL_DATA_ONLY = no
    GEODATABASE_FILE_SPLIT_COMPLEX_EDGES = no
    FEATURETYPES = N250_AdminFlate
    WHERE = @Value(_kommunewhere)
    SUPPORTED_SPATIAL_INTERACTIONS = ENVELOPE_INTERSECT%INTERSECTS%CONTAINS%CROSSES%DISJOINT%EQUALS%OVERLAPS%TOUCHES%WITHIN
    GEODATABASE_FILE_FEATURE_READ_MODE = Features
    DATASET = K:\Vektor\00\23-N250\00\EsriGDB\N250.gdb
    COMBINE_ATTRS = Keep result attributes only
    GEODATABASE_FILE_SPLIT_MULTI_PART_ANNOS = no
    GEODATABASE_FILE_IGNORE_NETWORK_INFO = yes
    GEODATABASE_FILE_IGNORE_RELATIONSHIP_INFO = yes
    GEODATABASE_FILE_TABLELIST = N250_AdminFlate
    GEODATABASE_FILE_RESOLVE_DOMAINS = no
    GEODATABASE_FILE_RESOLVE_SUBTYPE_NAMES = yes
    FORMAT = GEODATABASE_FILE
    COMBINE_GEOM = Keep result geometry only
    ATTRIBUTES = N250_AdminFlate,"geodb_oid,OBJECTID,OBJTYPE,NAVN,KOMM,OPPDATERINGSDATO,Shape_Length,Shape_Area"
    N250_AdminFlate -> Dissolver
Dissolver
    NO_OVRLP = No
    ACCUM_INPUT_ATTRS = No
    AREA -> DonutHoleExtractor
DonutHoleExtractor
    OUTERSHELL -> FeatureReader_2
Note: CurveSegment, RefLinkPart og RefNode
FeatureReader_2
    SUPPORTED_SPATIAL_INTERACTIONS = ENVELOPE_INTERSECT%INTERSECTS%CONTAINS%CROSSES%DISJOINT%EQUALS%OVERLAPS%TOUCHES%WITHIN
    GEODATABASE_SDE_SEARCH_ORDER = SPATIAL_FIRST
    FEATURETYPES = SDE_TNE.TNE_CurveSegment SDE_TNE.TNE_RefLinkPart SDE_TNE.TNE_RefNode
    GEODATABASE_SDE_SPLIT_COMPLEX_ANNOS = no
    GEODATABASE_SDE_ALIAS_MODE = NONE
    GEODATABASE_SDE_IGNORE_RELATIONSHIP_INFO = yes
    GEODATABASE_SDE_CONNECTION_FILE = C:\Users\knjetl\AppData\Roaming\ESRI\Desktop10.2\ArcCatalog\PTNE-sde_tne_read@svvkartp.vegvesen.no.sde
    GEODATABASE_SDE_SPLIT_COMPLEX_EDGES = no
    GEODATABASE_SDE_MERGE_FEAT_LINKED_ANNOS = no
    GEODATABASE_SDE_CREDENTIALS_OVERRIDE = NO
    INTERACT = Intersects
    GEODATABASE_SDE_VERSION_OVERRIDE = NO
    GEODATABASE_SDE_SEARCH_METHOD = GEODB_INTERSECTS
    GEODATABASE_SDE_REMOVE_TABLE_QUALIFIER = NO
    COMBINE_GEOM = Use Result
    ATTR_ACCUM_MODE = Merge Initiator and Result
    FORMAT = GEODATABASE_SDE
    GEODATABASE_SDE_TRANSLATE_SPATIAL_DATA_ONLY = no
    GEODATABASE_SDE_RESOLVE_SUBTYPE_NAMES = yes
    GEODATABASE_SDE_CHECK_SIMPLE_GEOM = no
    GEODATABASE_SDE_QUERY_FEATURE_TYPES_FOR_MERGE_FILTERS = Yes
    WHERE = TO_DATE = 99991231
    GEODATABASE_SDE_CLIP_TO_ENVELOPE = NO
    ATTR_CONFLICT_RES = Use Result
    GEODATABASE_SDE_FEATURE_READ_MODE = Features
    GEODATABASE_SDE_RESOLVE_DOMAINS = no
    FEATURETYPES_RADIO = FEATURETYPES
    GEODATABASE_SDE_CACHE_MULTIPATCH_TEXTURES = yes
    GEODATABASE_SDE_SPLIT_MULTI_PART_ANNOS = no
    GEODATABASE_SDE_USE_SEARCH_ENVELOPE = NO
    ATTRIBUTES = SDE_TNE.TNE_CurveSegment,"OBJECTID,REFLINK_OID,FROM_DATE,TO_DATE,FROM_MEASURE,TO_MEASURE,SEG_DATE,LENGTH,CLASS_CODE,OBJECT_CODE,MEDIUM,QUALITY_METHOD,QUALITY_ACCURACY,QUALITY_VISIBILITY,QUALITY_METHOD_HEIGHT,QUALITY_ACCURACY_HEIGHT,QUALITY_TOLERANCE,MUNICIPALITY,SHAPE.LEN",SDE_TNE.TNE_RefLinkPart,"OBJECTID,REFLINK_OID,FROM_DATE,TO_DATE,FROM_MEASURE,TO_MEASURE,FROM_REFNODE_OID,TO_REFNODE_OID,LENGTH,TOPOLOGY_LEVEL,SUPER_OID,SUPER_FROM_MEASURE,SUPER_TO_MEASURE,LANE,DIRECTION,SHAPE.LEN",SDE_TNE.TNE_RefNode,"OBJECTID,OID,VID,REFOBJ_TYPE,NEXT_FREE_PORT_NUMBER,FROM_DATE,TO_DATE"
    GEODATABASE_SDE_PERSISTENT_CONNECTION = no
    GEODATABASE_SDE_IGNORE_NETWORK_INFO = yes
    SDE_TNE.TNE_RefLinkPart -> PythonCaller_3
Note: Finner valgt detaljnivå
PythonCaller_3
    PYTHONSOURCE:
      import fmeobjects

      def topolevel(feature):
          par = '0,1,2,3'
          if FME_MacroValues['detaljNivå'] == 'Vegtrase':
              par = '0,1'
          elif FME_MacroValues['detaljNivå'] == 'Kjørebane':
              par = '1,2'
          elif FME_MacroValues['detaljNivå'] == 'Kjørefelt':
              par = '1,2,3'
          feature.setAttribute("_topoWhere", par)
    PYTHONSYMBOL = topolevel
    NEW_ATTRIBUTES = _topoWhere
    -> TestFilter_4
Note: Finner lenker som skal være med
TestFilter_4
    TEST_LIST = BOOL_OP,OR,COMPOSITE_TEST,<Unused>,TEST_CLAUSE,"TEST @Value(TOPOLOGY_LEVEL) IN @Value(_topoWhere)",TOPOLEVEL
    DEFAULT_VALUE = <UNFILTERED>
    TOPOLEVEL -> TestFilter_4_TOPOLEVEL
TestFilter_4_TOPOLEVEL: Inspector
Veglenke (writer GML_1)
    attributes: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
Vegnode (writer GML_1)
    attributes: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
Veglenkesett (writer GML_1)
    attributes: identifikasjon xml_xml, nettverk.nilReason xml_buffer, nettverk.gml_remoteSchema xml_buffer, nettverk.xlink_href xml_buffer, nettverk.owns xml_boolean, lenke{}.nilReason xml_buffer, lenke{}.gml_remoteSchema xml_buffer, lenke{}.xlink_href xml_buffer, lenke{}.owns xml_boolean
Veglenkesekvens (writer GML_1)
    attributes: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
Nettverk (writer GML_1)
    attributes: nettverkselement{}.nilReason xml_buffer, nettverkselement{}.gml_remoteSchema xml_buffer, nettverkselement{}.xlink_href xml_buffer, nettverkselement{}.owns xml_boolean
