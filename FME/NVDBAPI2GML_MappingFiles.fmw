FME workspace NVDBAPI2GML_MappingFiles.fmw

Parameters:
- gmlName = Stikkrenne   # GML file and schema name
- ftID = 79   # NVDB feature type ID
- Kommuner = 520   # komm
- xsdFolder = C:\DATA\GitHub\NVDBGML\XSD\NIFS   # XSD Main folder
- gmlNamespace = https://raw.githubusercontent.com/jetgeo/NVDBGML/master/XSD/NIFS   # GML Namespace
- gmlFolder = C:\DATA\GitHub\NVDBGML\GML\NIFS\0520   # Output GML folder
- xfmap_api = $(FME_MF_DIR)API_Mapping.xmp   # xfMap for API-mapping
- coordsys = EPSG:25833   # Koordinatsystem
- namespace = vegvesen.no.nvdb   # Attribute Value
- maxFeatures = 10000   # Maximal number of features
- mfET:   # Python Script
      mfLC = FME_MacroValues['xsdFolder'] + '\\' + FME_MacroValues['gmlName'] + '_enMapping.csv'
      return mfLC

Writers:
- GML_1: GML to $(gmlFolder)

Creator
    GEOMTYPE = Geometry Object
    NUM = 1
    CREATED -> AttributeCreator_3
AttributeCreator_3
    ATTR_LIST = ftID,$(ftID)
    -> AttributeSplitter
AttributeSplitter
    ATTR_NAME = ftID
    DROP_EMPTY_PARTS = No
    TRIM_OPTION = Both
    DELIMITER = ,
    LIST_NAME = _ftID
    -> ListExploder
ListExploder
    INDEX_ATTR = _element_index
    ATTR_ACCUM_MODE = Merge Incoming List
    LIST_ATTR = _ftID{}
    ATTR_CONFLICT_RES = Use Original
    LIST_FOUND -> AttributeCreator
    LIST_FOUND -> AttributeCreator_2
    NOT_FOUND -> AttributeCreator_2
    NOT_FOUND -> AttributeCreator
AttributeCreator [off]
    ATTR_LIST = _api,https://www.vegvesen.no/nvdb/api/sok?kriterie={objektTyper:[{id:@Value(_ftID),antall:$(maxFeatures)}]},_gmlFeatureType,$(gmlName)
    NUM_SUBSEQUENT_FEATURES = 0
    NUM_PRIOR_FEATURES = 0
Note: AttributeCreator_2 [AttributeCreator:6] / Number of Prior Features: 0 / Number of Subsequent Features: 0 / _api = https://www.vegvesen.no/nvdb/api/sok?kriterie={lokasjon:{kommune: [$(Kommuner)]},objektTyper:[{id:@Value(_ftID),antall:$(maxFeatures)}]} / Version: 6 / Latest Version: 8 / Last Parameter Edit: Build 15479
AttributeCreator_2
    ATTR_LIST = _api,https://www.vegvesen.no/nvdb/api/sok?kriterie={lokasjon:{kommune: [$(Kommuner)]},objektTyper:[{id:@Value(_ftID),antall:$(maxFeatures)}]}
    NUM_SUBSEQUENT_FEATURES = 0
    NUM_PRIOR_FEATURES = 0
    -> NVDBAPI2GML
NVDBAPI2GML
    coordsys = $(coordsys)
    mfET:
      mfLC = FME_MacroValues['mfLocalPrefix']+ '_enMapping.csv'
      return mfLC
    mfPT:
      mfLC = FME_MacroValues['mfLocalPrefix']+ '_ptMapping.csv'
      return mfLC
    mfLocalPrefix = $(xsdFolder)\$(gmlName)
    mfFT:
      mfLC = FME_MacroValues['mfLocalPrefix']+ '_ftMapping.csv'
      return mfLC
    _API = @Value(_api)
    namespace = $(namespace)
    xfmap_api = $(xfmap_api)
    -> Vegobjekttype (writer GML_1)
Vegobjekttype (writer GML_1)
    attributes: _creation_instance xml_char(200), ftID xml_char(200), _ftID xml_char(200), _element_index xml_char(200), _api xml_char(200), _headers{}.name xml_char(200), _headers{}.value xml_char(200), _error xml_char(200), _http_status_code xml_char(200), _url_contents xml_char(200), egengeometri xml_char(200), vegreferanse{}.vegkategori xml_char(200), vegreferanse{}.vegnummer xml_char(200), vegreferanse{}.vegstatus xml_char(200), vegreferanse{}.hovedParsell xml_char(200), vegreferanse{}.veglenkeMeterFra xml_char(200), vegreferanse{}.veglenkeMeterTil xml_char(200), assosiasjon{}.typeId xml_char(200), assosiasjon{}.uri xml_char(200), _xml_feature_count_ xml_char(200), _xml_source_ xml_char(200), _schemamapper_row_ids xml_char(200), identifikasjon.Identifikasjon.lokalId xml_buffer, identifikasjon.Identifikasjon.versjonId xml_char(200), identifikasjon.Identifikasjon.navnerom xml_buffer, name xml_char(200), prosesshistorie xml_char(200), lineærPosisjon.LineærPosisjonPunkt.lineærtObjektIdentifikasjon.Identifikasjon.lokalId xml_char(200), lineærPosisjon.LineærPosisjonPunkt.posisjon xml_char(200), lineærPosisjon.LineærPosisjonPunkt.tilPosisjon xml_char(200),
      lineærPosisjon.LineærPosisjonPunkt.felt xml_char(200), _element_count xml_char(200), lineærPosisjon.LineærPosisjonPunkt.lineærtObjektIdentifikasjon.Identifikasjon.navnerom xml_char(200), lineærPosisjon{}.LineærPosisjonStrekning.lineærtObjektIdentifikasjon.Identifikasjon.lokalId xml_char(200), lineærPosisjon{}.LineærPosisjonStrekning.fraPosisjon xml_char(200), lineærPosisjon{}.LineærPosisjonStrekning.tilPosisjon xml_char(200), lineærPosisjon{}.LineærPosisjonStrekning.felt xml_char(200), lineærPosisjon{}.identifikasjon.Identifikasjon.lokalId xml_char(200), lineærPosisjon{}._element_count xml_char(200), lineærPosisjon{}._element_index xml_char(200), lineærPosisjon{}.LineærPosisjonStrekning.lineærtObjektIdentifikasjon.Identifikasjon.navnerom xml_char(200)

FME custom transformer NVDBAPI2GML

Parameters:
- xfmap_api = $(FME_MF_DIR)API_Mapping.xmp   # xfMap for API-mapping
- namespace = vegvesen.no.nvdb   # Attribute Value
- coordsys = EPSG:25833   # Koordinatsystem
- mfLocalPrefix =   # Prefiks for mappingfiler
- _API = @Value(_api)   # Api
- mfPT:   # Python Script
      mfLC = FME_MacroValues['mfLocalPrefix']+ '_ptMapping.csv'
      return mfLC
- mfFT:   # Python Script
      mfLC = FME_MacroValues['mfLocalPrefix']+ '_ftMapping.csv'
      return mfLC
- mfET:   # Python Script
      mfLC = FME_MacroValues['mfLocalPrefix']+ '_enMapping.csv'
      return mfLC

Input (input)
    -> HTTPFetcher_2
Note: Henter objekter fra NVDB-API
HTTPFetcher_2
    SAVE_FILE = No
    VERIFY_SSL_CERTIFICATES = Yes
    USE_COOKIES = No
    STATUS_CODE_ATTR = _http_status_code
    TARGET_URL = @Value(_api)
    ERROR_ATTR = _error
    FOLLOW_REDIRECTS = Yes
    PROXY_AUTH_METHOD = Basic
    REQUEST_HEADER:
      GET /vegobjekter HTTP/1.1
      Accept: application/vnd.vegvesen.nvdb-v1+xml
    AUTH_METHOD = Basic
    RESPONSE_HEADER_LIST_ATTR = _headers
    TARGET_ATTR = _url_contents
    -> XMLFeatureMapper
Note: Tolker XML
XMLFeatureMapper
    ATTRIBUTE_XML = _url_contents
    MERGE_ATTRS = Yes
    SINGLE_XFMAP = $(xfmap_api)
    CONFIGURATION_TYPE = Single xfMap file
    XML_INPUT_TYPE = Attribute with XML document
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt assosiasjon{}.typeId assosiasjon{}.uri
    XML_SOURCE_NAME = _xml_source_
    FEATURE_COUNT_PER_XML = _xml_feature_count_
    FEATURE_TYPE_ATTR = fme_feature_type
    MAPPED -> GeometryReplacer
Note: Tildeler geometri
GeometryReplacer
    KIND_LONG = OGC Well Known Text
    SOURCE = @Value(geometriUtm33)
    REMOVE_ATTRIBUTE = Yes
    OGC_WKT_PRECISION_DISPLAY = 64-bit
    -> CoordinateSystemSetter
CoordinateSystemSetter
    COORDSYS = $(coordsys)
    -> SchemaMapper
Note: SchemaMapper [SchemaMapper:1] / Table Type: CSV / Source: $(mfET) / Table: CSV / Version: 1 / Last Parameter Edit: Build 16481
Note: Mapper tillatte verdier til GML-verdier
SchemaMapper
    CSV__FIELD_NAMES_AFTER_HEADER = no
    CSV_SCAN_MAX_FEATURES = 1000
    CSV__SCHEMA_WITH_COL_NAMES = ptid,number,6,0,enid,number,6,0,name,char,28,,fullname,char,36,
    MATCH_ATTRS = ptid fullname
    IDXDESTCOL = ""
    CSV__DUPLICATE_DELIMS = no
    CSV__STRIP_QUOTES = yes
    TABLE = CSV
    CSV__IN_FIELD_NAMES = YES
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ptid%enid%name%fullname\"%%\"Filter\"%\"STRING_ENCODED _FILTER_REGEX \"%%\"Invert Filter\"%\"CHECKBOX _FILTER_UNMATCHED yes%no\"%no"
    CSV__SKIP_LINES = 1
    DATASET = $(mfET)
    ROW_ID_ATTR = _schemamapper_row_ids
    IDXSOURCECOL = ""
    CSV__GROUP_BY_DATASET = no
    MAP_ATTRS = fullname ptid name
    CSV__SCHEMA = number,6,0,number,6,0,char,28,,char,36,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ptid%enid%name%fullname\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_SEPARATOR = ;
    CSV__ALLOW_SPACES_IN_COLUMN_NAMES = yes
    FORMAT = CSV
    IDXSOURCEATTR = fme_feature_type
    IDXDESTATTR = fme_feature_type
    MAPPED -> SchemaMapper_2
    UNMAPPED -> SchemaMapper_2
Note: Mapper egenskapsnavn til GML, vha koblingstabell
Note: SchemaMapper_2 [SchemaMapper:1] / Table Type: CSV / Source: $(mfPT) / Table: CSV / Version: 1 / Last Parameter Edit: Build 15479
SchemaMapper_2
    CSV__FIELD_NAMES_AFTER_HEADER = no
    CSV_SCAN_MAX_FEATURES = 1000
    CSV__SCHEMA_WITH_COL_NAMES = ft_attr,char,17,,ftid,number,3,0,ptid,number,6,0,name,char,22,
    MATCH_ATTRS = ft_attr ftid
    IDXDESTCOL = ""
    CSV__DUPLICATE_DELIMS = no
    CSV__STRIP_QUOTES = yes
    TABLE = CSV
    CSV__IN_FIELD_NAMES = YES
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ft_attr%ftid%ptid%name\"%%\"Filter\"%\"STRING_ENCODED _FILTER_REGEX \"%%\"Invert Filter\"%\"CHECKBOX _FILTER_UNMATCHED yes%no\"%no"
    CSV__SKIP_LINES = 1
    DATASET = $(mfPT)
    ROW_ID_ATTR = _schemamapper_row_ids
    IDXSOURCECOL = ""
    CSV__GROUP_BY_DATASET = no
    MAP_ATTRS = ptid name """"""
    CSV__SCHEMA = char,17,,number,3,0,number,6,0,char,22,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ft_attr%ftid%ptid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_SEPARATOR = ;
    CSV__ALLOW_SPACES_IN_COLUMN_NAMES = yes
    FORMAT = CSV
    IDXSOURCEATTR = fme_feature_type
    IDXDESTATTR = fme_feature_type
    MAPPED -> NullAttributeMapper_3
NullAttributeMapper_3
    SOURCE_ATTR_VAL = Empty Null
    ATTRCHOICE = All Attributes
    NULL_TREATMENT = Missing
    -> SchemaMapper_3
Note: Mapperobjekttypenavn til GML, vha koblingstabell
Note: SchemaMapper_3 [SchemaMapper:1] / Table Type: CSV / Source: $(mfFT) / Table: CSV / Version: 1 / Last Parameter Edit: Build 15479
SchemaMapper_3
    CSV__FIELD_NAMES_AFTER_HEADER = no
    CSV_SCAN_MAX_FEATURES = 1000
    CSV__SCHEMA_WITH_COL_NAMES = ftid,number,3,0,name,char,18,
    IDXDESTCOL = name
    CSV__DUPLICATE_DELIMS = no
    CSV__STRIP_QUOTES = yes
    TABLE = CSV
    CSV__IN_FIELD_NAMES = YES
    CSV__SKIP_FOOTER = 0
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES ftid%name\"%%\"Filter\"%\"STRING_ENCODED _FILTER_REGEX \"%%\"Invert Filter\"%\"CHECKBOX _FILTER_UNMATCHED yes%no\"%no"
    CSV__SKIP_LINES = 1
    DATASET = $(mfFT)
    ROW_ID_ATTR = _schemamapper_row_ids
    IDXSOURCECOL = ftid
    CSV__GROUP_BY_DATASET = no
    CSV__SCHEMA = number,3,0,char,18,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES ftid%name\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__IN_SEPARATOR = ;
    CSV__ALLOW_SPACES_IN_COLUMN_NAMES = yes
    FORMAT = CSV
    IDXSOURCEATTR = fme_feature_type
    IDXDESTATTR = fme_feature_type
    MAPPED -> AttributeExposer_3
AttributeExposer_3
    ATTR_LIST = NVDB_ID,versjonsId
    -> AttributeRenamer_2
Note: ID
AttributeRenamer_2
    ATTR_LIST = NVDB_ID,identifikasjon.Identifikasjon.lokalId,"","",identifikasjon.Identifikasjon.navnerom,$(namespace),versjonsId,identifikasjon.Identifikasjon.versjonId,""
    -> ListExploder_3
    -> FeatureMerger_3 [REQUESTOR]
FeatureMerger_3
    SUPPLIERS_FIRST = No
    MERGE_TYPE = Attributes Only
    ATTR_ACCUM_MODE = Merge Supplier
    IGNORE_NULLS = No
    JOIN_KEYS = @Value(identifikasjon.Identifikasjon.lokalId) @Value(identifikasjon.Identifikasjon.lokalId) AUTO
    PROCESS_DUPS = No
    ATTR_CONFLICT_RES = Use Requestor
    REJECT_NULL_MISSING_KEYS = No
    MERGED -> GeometryFilter
    NOT_MERGED -> GeometryFilter
AttributeValueMapper_2
    DIRECTION = Forward (Source To Destination)
    LUT = true,Geometri: Egengeometri fra NVDB
    DEFAULT_VALUE = Geometri: Generert fra lineære referanser til vegnett i NVDB
    VAL_ATTR = prosesshistorie
    SRC = egengeometri
    -> AttributeKeeper
    -> AttributeRemover
AttributeRemover
    LIST_ATTRS = lineærPosisjon{}
    -> FeatureMerger [REQUESTOR]
AttributeKeeper
    KEEP_LIST = lineærPosisjon{}.felt lineærPosisjon{}.fraPosisjon lineærPosisjon{}.tilPosisjon lineærPosisjon{}.lineærtObjektIdentifikasjon.Identifikasjon.lokalId
    KEEP_ATTRS = identifikasjon.Identifikasjon.lokalId
    -> ListElementCounter
ListElementCounter
    CNT_ATTR = _element_count
    LIST_NAME = lineærPosisjon{}
    -> TestFilter
TestFilter
    TEST_LIST:
      BOOL_OP,AND,COMPOSITE_TEST,<Unused>,TEST_CLAUSE,"TEST @Value(lineærPosisjon{0}.fraPosisjon) = @Value(lineærPosisjon{0}.tilPosisjon)
      TEST @Value(_element_count) = 1",Punkt
    DEFAULT_VALUE = Strekning
    Punkt -> ListExploder
    Strekning -> ListExploder_2
FeatureMerger
    SUPPLIERS_FIRST = No
    MERGE_TYPE = Attributes Only
    ATTR_ACCUM_MODE = Merge Supplier
    IGNORE_NULLS = No
    JOIN_KEYS = @Value(identifikasjon.Identifikasjon.lokalId) @Value(identifikasjon.Identifikasjon.lokalId) AUTO
    PROCESS_DUPS = No
    ATTR_CONFLICT_RES = Use Requestor
    MERGED -> AttributeCreator_2
    NOT_MERGED -> AttributeCreator_2
AttributeCreator_2
    ATTR_LIST = gml_id,$(namespace).@Value(identifikasjon.Identifikasjon.lokalId)
    -> Output (output)
Output (output)

Bookmark: Eksploderer gjeldende liste og kobler til objekttypenavn
ListExploder_3
    INDEX_ATTR = _element_index
    ATTR_ACCUM_MODE = Merge Incoming List
    LIST_ATTR = assosiasjon{}
    ATTR_CONFLICT_RES = Use Incoming List
    ELEMENTS -> AttributeKeeper_2
AttributeKeeper_2
    KEEP_ATTRS = typeId,uri,identifikasjon.Identifikasjon.versjonId,identifikasjon.Identifikasjon.lokalId,identifikasjon.Identifikasjon.navnerom
    -> Joiner
Joiner
    JOIN_KEYS = typeId ftid
    CSV__FIELD_NAMES_AFTER_HEADER = no
    ADDED_FIELDS = name
    FORMAT = CSV
    CSV__DUPLICATE_DELIMS = no
    CSV__SKIP_FOOTER = 0
    ATTR_CONFLICT_RES = Use Original
    DATASET = $(mfFT)
    MATCH_RULE_DISPLAY = Match All (1:M)
    CSV__SCHEMA_WITH_COL_NAMES = ftid,number,4,0,name,char,23,
    CSV__STRIP_QUOTES = yes
    CSV_SCAN_MAX_FEATURES = 1000
    CSV__SCHEMA = number,4,0,char,23,
    CSV__GROUP_BY_DATASET = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__IN_SEPARATOR = ;
    CSV__ALLOW_SPACES_IN_COLUMN_NAMES = yes
    CSV__SKIP_LINES = 1
    TABLE = CSV
    MATCH_MULTIPLE_DISPLAY = Create a feature for each match
    CSV__IN_FIELD_NAMES = YES
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    ATTR_ACCUM_MODE = Merge Joined
    JOINED -> AttributeSplitter_3

Bookmark: Ordner NVDB-id og lager xlink_href for hver assosiasjon
AttributeSplitter_3
    ATTR_NAME = uri
    DROP_EMPTY_PARTS = No
    TRIM_OPTION = Both
    DELIMITER = /
    LIST_NAME = _list
    -> ListIndexer_2
ListIndexer_2
    LIST_ATTR = _list{}
    INDEX = 3
    -> AttributeRenamer_4
AttributeRenamer_4
    ATTR_LIST = assosiertID,_list
    -> ListRemover_2
ListRemover_2
    LIST_ATTRS = _list{}
    -> StringConcatenator
StringConcatenator
    PARM_LINE = @Value(name).gml#$(namespace).@Value(assosiertID)
    ACTION = Create New Attribute
    VAL_ATTR = xlink_href
    -> AttributeKeeper_3

Bookmark: Lager assosiasjonsliste pr objekttype pr objekt
AttributeKeeper_3
    KEEP_ATTRS = identifikasjon.Identifikasjon.versjonId,name,identifikasjon.Identifikasjon.lokalId,identifikasjon.Identifikasjon.navnerom,xlink_href
    -> ListBuilder_2
ListBuilder_2
    GRP_BY = identifikasjon.Identifikasjon.versjonId name identifikasjon.Identifikasjon.lokalId identifikasjon.Identifikasjon.navnerom
    LIST_NAME = _list
    -> PythonCaller
PythonCaller
    PYTHONSYMBOL = processFeature
    PYTHONSOURCE:
      import fme
      import fmeobjects

      def processFeature(feature):
          anames= feature.getAllAttributeNames()
          lname = "blank"
          #find name attribute value
          for aname in anames:
              if aname == "name":
                  lname = feature.getAttribute(aname)
          #find list attributes and rename/copy to new name
          if lname != "blank":
              for aname in anames:
                  if aname.startswith("_list{"):
                      newAname=aname.replace("_list{","assosiert"+lname+"{")
                      aval = feature.getAttribute(aname)
                      feature.setAttribute(newAname, aval)
    -> AttributeRemover_2
AttributeRemover_2
    LIST_ATTRS = _list{}
    -> FeatureMerger_3 [SUPPLIER]

Bookmark: Definerer geometriegenskaper
GeometryFilter
    BREAK_AGG = No
    GEOM_PORT_NAMES = Point Line Area
    POINT -> GeometryPropertySetter
    LINE -> LineJoiner
    LINE -> FeatureMerger_2 [SUPPLIER]
    AREA -> GeometryPropertySetter_3
GeometryPropertySetter
    OVERWRITE_CHOICE = Yes
    GEOM_NAME_FIELD = posisjon
    SETTYPE_PARAM = Geometry Name
    SET -> AttributeValueMapper_2
GeometryPropertySetter_3
    OVERWRITE_CHOICE = Yes
    GEOM_NAME_FIELD = område
    SETTYPE_PARAM = Geometry Name
    SET -> AttributeValueMapper_2
Note: Slår sammen linjesegmenter
LineJoiner
    GROUP_BREAK = no
    BREAK = no
    TOPOLOGY = End noded
    PRESERVE = no
    GROUP_BY = identifikasjon.Identifikasjon.lokalId
    CONSIDER_NODE_ELEVATION = no
    LINES_AS_SEGMENTS = No
    LINE -> FeatureMerger_2 [REQUESTOR]
FeatureMerger_2
    SUPPLIERS_FIRST = No
    MERGE_TYPE = Attributes Only
    ATTR_ACCUM_MODE = Merge Supplier
    IGNORE_NULLS = No
    JOIN_KEYS = @Value(identifikasjon.Identifikasjon.lokalId) @Value(identifikasjon.Identifikasjon.lokalId) AUTO
    PROCESS_DUPS = No
    ATTR_CONFLICT_RES = Use Requestor
    MERGED -> GeometryPropertySetter_4
GeometryPropertySetter_4
    OVERWRITE_CHOICE = Yes
    GEOM_NAME_FIELD = senterlinje
    SETTYPE_PARAM = Geometry Name
    SET -> AttributeValueMapper_2

Bookmark: Lager lineærPosisjon (punkt)
ListExploder
    INDEX_ATTR = _element_index
    INCOMING_PREFIX = lineærPosisjon.LineærPosisjonPunkt.
    ATTR_ACCUM_MODE = Prefix Incoming List
    LIST_ATTR = lineærPosisjon{}
    LIST_FOUND -> AttributeRenamer
AttributeRenamer
    ATTR_LIST = lineærPosisjon.LineærPosisjonPunkt.fraPosisjon,lineærPosisjon.LineærPosisjonPunkt.posisjon,,,lineærPosisjon.LineærPosisjonPunkt.lineærtObjektIdentifikasjon.Identifikasjon.navnerom,$(namespace).rl
    -> FeatureMerger [SUPPLIER]

Bookmark: Lager lineærPosisjon-liste (strekning)
ListExploder_2
    INDEX_ATTR = _element_index
    INCOMING_PREFIX = LineærPosisjonStrekning.
    ATTR_ACCUM_MODE = Prefix Incoming List
    LIST_ATTR = lineærPosisjon{}
    LIST_FOUND -> AttributeCreator
AttributeCreator
    ATTR_LIST = LineærPosisjonStrekning.lineærtObjektIdentifikasjon.Identifikasjon.navnerom,$(namespace).rl
    -> ListBuilder
ListBuilder
    GRP_BY = identifikasjon.Identifikasjon.lokalId
    LIST_NAME = lineærPosisjon
    -> FeatureMerger [SUPPLIER]
