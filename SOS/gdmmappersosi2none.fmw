FME workspace gdmmappersosi2none.fmw

Parameters:
- SourceDataset_GDMMAPPERSOSI = ""$(FME_MF_DIR)NVDB_Kum_83_mal_33.sos" "$(FME_MF_DIR)Nye_veiobjekter_på_driftskontrakt_1603_Stikkrenne-Kulvert_79.sos" "$(FME_MF_DIR)RV150_NVDB_Kantstein_9_Tunnel_UTM32.sos" "$(FME_MF_DIR)RV150_NVDB_Nødstasjon_500_UTM32.sos" "$(FME_MF_DIR)RV150_NVDB_Temperaturmåler_463_UTM32.sos""   # Source GDM File

Readers:
- GDMMAPPERSOSI_1: GDMMAPPERSOSI from $(SourceDataset_GDMMAPPERSOSI)

Nødstasjon_500 (reader GDMMAPPERSOSI_1)
    attributes: OBJTYPE char(15), PLASSERING_4001 number(5,0)
    -> Nødstasjon_500
Nødstasjon_500: Inspector
Kum_83 (reader GDMMAPPERSOSI_1)
    attributes: BRUKSOMRÅDE char(10), BRUKSOMRÅDE_1269 number(5,0), BYGGEÅR_7065 number(5,0), DATAFANGSTDATO number(9,0), DIAMETER number(5,0), DIAMETER_1727 number(4,2), EIER char(17), EIER_5816 number(5,0), INNGÅRIDRENSSYSTEM_2122 number(5,0), INNGÅR_I_DRENSSYSTEM char(4), KVALITET.H-MÅLEMETODE number(3,0), KVALITET.H-NØYAKTIGHET number(2,0), KVALITET.MÅLEMETODE number(3,0), KVALITET.NØYAKTIGHET number(2,0), KVALITET.SYNBARHET number(2,0), LOKK/RIST_TYPE char(21), LOKKRISTTYPE_2290 number(5,0), MATERIALTYPE char(7), MATERIALTYPE_1411 number(5,0), OBJTYPE char(7), PTEMA number(4,0), TYPE char(13), TYPE_1141 number(5,0), VEDLIKEHOLDSANSVARLIG_5804 number(5,0)
    -> Kum_83
Kum_83: Inspector
StikkrenneKulvert_79 (reader GDMMAPPERSOSI_1)
    attributes: BRUKSOMRÅDE_6981 number(5,0), DATAFANGSTDATO number(9,0), DIAMETERINNVENDIG_3113 number(5,0), FRADATO number(9,0), FYLKE number(3,0), HARINNLØPSRIST_1923 number(5,0), HP number(2,0), KVALITET.H-MÅLEMETODE number(3,0), KVALITET.H-NØYAKTIGHET number(3,0), KVALITET.MÅLEMETODE number(3,0), KVALITET.NØYAKTIGHET number(3,0), KVALITET.SYNBARHET number(2,0), LEGGEÅR_4556 number(5,0), LENGDE_1323 number(5,2), MATERIALTYPE_6983 number(5,0), NVDBID number(6,0), OBJTYPE char(21), SIDE char(2), STATUS char(7), TILKNYTTETLUKKADREN_1941 number(5,0), TVERRSNITTSFORM_6984 number(5,0), TYKKELSEOVERFYLLING_3115 number(3,1), TYPE char(13), TYPEINNLØP_1939 number(6,0), TYPEUTLØP_1940 number(6,0), VARMEKABLER_1832 number(5,0), VEG char(6)
    -> StikkrenneKulvert_79
StikkrenneKulvert_79: Inspector
Kantstein_9 (reader GDMMAPPERSOSI_1)
    attributes: AVVISNING_4082 number(5,0), LTEMA number(4,0), MATERIALTYPE_1092 number(5,0), OBJTYPE char(12)
    -> Kantstein_9
Kantstein_9: Inspector
Temperaturmåler_463 (reader GDMMAPPERSOSI_1)
    attributes: ANTALL_5288 number(2,0), BRUKSOMRÅDE_5289 number(5,0), OBJTYPE char(20)
    -> Temperaturmåler_463
Temperaturmåler_463: Inspector
